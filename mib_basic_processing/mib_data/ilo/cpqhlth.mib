-- ****************************************************************************
--
--                         Server Health Features
--         Management Information Base for SNMP Network Management
--
--
--      Copyright 1992,2008 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQHLTH-MIB DEFINITIONS ::= BEGIN

    IMPORTS
        compaq                  FROM CPQHOST-MIB
        enterprises             FROM RFC1155-SMI
        Counter                 FROM RFC1155-SMI
        DisplayString           FROM RFC1213-MIB
        OBJECT-TYPE             FROM RFC-1212
        TRAP-TYPE               FROM RFC-1215
        sysName                 FROM RFC1213-MIB
        cpqHoTrapFlags          FROM CPQHOST-MIB
        cpqSiServerSystemId     FROM CPQSINFO-MIB
        cpqSiMemModuleSize      FROM CPQSINFO-MIB
	cpqHoGUIDCanonical      FROM CPQHOST-MIB;

--  compaq                  OBJECT IDENTIFIER ::= { enterprises 232 }
    cpqHealth               OBJECT IDENTIFIER ::= { compaq 6 }
    cpqHeMibRev             OBJECT IDENTIFIER ::= { cpqHealth 1 }
    cpqHeComponent          OBJECT IDENTIFIER ::= { cpqHealth 2 }
    cpqHeTrap               OBJECT IDENTIFIER ::= { cpqHealth 3 }

    cpqHeInterface          OBJECT IDENTIFIER ::= { cpqHeComponent 1 }
    cpqHeCriticalError      OBJECT IDENTIFIER ::= { cpqHeComponent 2 }
    cpqHeCorrectableMemory  OBJECT IDENTIFIER ::= { cpqHeComponent 3 }
    cpqHeAsr                OBJECT IDENTIFIER ::= { cpqHeComponent 5 }
    cpqHeThermal            OBJECT IDENTIFIER ::= { cpqHeComponent 6 }
    cpqHePostMsg            OBJECT IDENTIFIER ::= { cpqHeComponent 7 }
    cpqHeSysUtil            OBJECT IDENTIFIER ::= { cpqHeComponent 8 }
    cpqHeFltTolPwrSupply    OBJECT IDENTIFIER ::= { cpqHeComponent 9 }
    cpqHeIRC                OBJECT IDENTIFIER ::= { cpqHeComponent 10 }
    cpqHeEventLog           OBJECT IDENTIFIER ::= { cpqHeComponent 11 }
    cpqHeMgmtDisplay        OBJECT IDENTIFIER ::= { cpqHeComponent 12 }
    cpqHePowerConverter     OBJECT IDENTIFIER ::= { cpqHeComponent 13 }
    cpqHeResilientMemory    OBJECT IDENTIFIER ::= { cpqHeComponent 14 }
    cpqHePowerMeter         OBJECT IDENTIFIER ::= { cpqHeComponent 15 }
    cpqHeHWBios             OBJECT IDENTIFIER ::= { cpqHeComponent 16 }
    cpqHeSysBackupBattery   OBJECT IDENTIFIER ::= { cpqHeComponent 17 }

    cpqHeOsNetWare3x        OBJECT IDENTIFIER ::= { cpqHeInterface 1 }
    cpqHeOsCommon           OBJECT IDENTIFIER ::= { cpqHeInterface 4 }

-- ****************************************************************************
--   Health MIB Revision
--   ===================
--
-- The compaq enterprise               (1.3.6.1.4.1.232)
--      cpqHealth Group                (1.3.6.1.4.1.232.6)
--       cpqHeMibRev Group             (1.3.6.1.4.1.232.6.1)
--
--     An Insight Agent conforming to this document will return a
--     cpqHeMibRevMajor of one (1) and a cpqHeMibRevMinor of fifty three (53).
--
--
--    Implementation of the MibRev group is mandatory for all agents
--    supporting the Server Health MIB.
--
-- ****************************************************************************

    cpqHeMibRevMajor OBJECT-TYPE
        SYNTAX  INTEGER (1..65535)
        ACCESS  read-only
        STATUS  mandatory
        DESCRIPTION
            "The Major Revision level of the MIB.

            A change in the major revision level represents a major change
            in the architecture of the MIB.  A change in the major revision
            level may indicate a significant change in the information
            supported and/or the meaning of the supported information,
            correct interpretation of data may require a MIB document with
            the same major revision level."
        ::= { cpqHeMibRev 1 }

    cpqHeMibRevMinor OBJECT-TYPE
        SYNTAX  INTEGER (0..65535)
        ACCESS  read-only
        STATUS  mandatory
        DESCRIPTION
            "The minor revision level of the MIB.

            A change in the minor revision level may represent some minor
            additional support, no changes to any pre-existing information
            has occurred."
        ::= { cpqHeMibRev 2 }

    cpqHeMibCondition OBJECT-TYPE
        SYNTAX  INTEGER {
            other(1),
            ok(2),              -- default
            degraded(3),
            failed(4)
            }
        ACCESS  read-only
        STATUS  mandatory
        DESCRIPTION
            "The overall condition.

             This object represents the overall status of the server health
             system represented by this MIB."
        ::= { cpqHeMibRev 3 }

-- ****************************************************************************
--   Health MIB NetWare OS Group
--   ===========================
--
-- The compaq enterprise               (1.3.6.1.4.1.232)
--      cpqHealth Group                (1.3.6.1.4.1.232.6)
--       cpqHeComponent Group          (1.3.6.1.4.1.232.6.2)
--        cpqHeInterface Group         (1.3.6.1.4.1.232.6.2.1)
--         cpqHeOsNetWare3x Group      (1.3.6.1.4.1.232.6.2.1.1)
--
--  Implementation of the cpqHeOsNetWare3x group is mandatory for all
--  agents that support the Server Health MIB in a NetWare host
--  operating environment.
--
-- ****************************************************************************

    cpqHeNw3xDriverName OBJECT-TYPE
        SYNTAX  DisplayString (SIZE (0..255))
        ACCESS  read-only
        STATUS  deprecated
        DESCRIPTION
            "Driver Name.

            This value identifies the NetWare Loadable Module providing the
            operating system access to the Server Health information."
        ::= { cpqHeOsNetWare3x 1 }

    cpqHeNw3xDriverDate OBJECT-TYPE
        SYNTAX  DisplayString (SIZE (8))
        ACCESS  read-only
        STATUS  deprecated
        DESCRIPTION
            "Driver Date.

            The date of the NetWare Loadable Module providing the operating
            system access to the Server Health logs.  The date is
            provided in mm/dd/yy format."
        ::= { cpqHeOsNetWare3x 2 }

    cpqHeNw3xDriverVersion OBJECT-TYPE
        SYNTAX  DisplayString (SIZE (0..5))
        ACCESS  read-only
        STATUS  deprecated
        DESCRIPTION
            "Driver Version.

            This is the version of the NetWare Loadable Module (NLM)
            providing the operating system access to the Server
            Health logs."
        ::= { cpqHeOsNetWare3x 3 }

-- ****************************************************************************
--   Health MIB OS Common Group
--   ==========================
--
-- The compaq enterprise               (1.3.6.1.4.1.232)
--      cpqHealth Group                (1.3.6.1.4.1.232.6)
--       cpqHeComponent Group          (1.3.6.1.4.1.232.6.2)
--        cpqHeInterface Group         (1.3.6.1.4.1.232.6.2.1)
--         cpqHeOsCommon Group         (1.3.6.1.4.1.232.6.2.1.4)
--
--  The cpqHeOsCommon group describes the interface to the Server
--  health components.  This information describes the interface modules
--  and general OS interface architectural information.
--
--  Implementation of the cpqHeOsCommon group is mandatory for all
--  agents that support the Server Health MIB.
--
-- ****************************************************************************

    cpqHeOsCommonPollFreq OBJECT-TYPE
        SYNTAX  INTEGER (0..65535)
        ACCESS  read-write
        STATUS  mandatory
        DESCRIPTION
            "The Insight Agent's polling frequency.

            The frequency, in seconds, at which the Insight Agent requests
            information from the device driver.  A frequency of zero
            indicates that the Insight Agent retrieves the information upon
            request of a management station, it does not poll the device
            driver at a specific interval.

            If the poll frequency is 0 all attempts to write to this
            object will fail.  If the poll frequency is non-zero,
            setting this value will change the polling frequency of the
            Insight Agent.  Setting the poll frequency to zero will always
            fail, an agent may also choose to fail any request to change
            the poll frequency to a value that would severely impact system
            performance."
        ::= { cpqHeOsCommon 1 }

-- ****************************************************************************
--   Health MIB OS Common Module Table
--   =================================
--
-- The compaq enterprise               (1.3.6.1.4.1.232)
--      cpqHealth Group                (1.3.6.1.4.1.232.6)
--       cpqHeComponent Group          (1.3.6.1.4.1.232.6.2)
--        cpqHeInterface Group         (1.3.6.1.4.1.232.6.2.1)
--         cpqHeOsCommon Group         (1.3.6.1.4.1.232.6.2.1.4)
--           cpqHeOsCommonModuleTable  (1.3.6.1.4.1.232.6.2.1.4.2) deprecated
--
-- ****************************************************************************

    cpqHeOsCommonModuleTable OBJECT-TYPE
        SYNTAX  SEQUENCE OF CpqHeOsCommonModuleEntry
        ACCESS  not-accessible
        STATUS  deprecated
        DESCRIPTION
            "Supporting software table.

             This is a table of software modules that provide an interface
             to the device this server health MIB describes."
        ::= { cpqHeOsCommon 2 }

    cpqHeOsCommonModuleEntry OBJECT-TYPE
        SYNTAX  CpqHeOsCommonModuleEntry
        ACCESS  not-accessible
        STATUS  deprecated
        DESCRIPTION
            "A description of a software modules that provide an interface
            to the device this MIB describes."
        INDEX   { cpqHeOsCommonModuleIndex }
        ::= { cpqHeOsCommonModuleTable 1 }

        CpqHeOsCommonModuleEntry ::= SEQUENCE {
            cpqHeOsCommonModuleIndex       INTEGER,
            cpqHeOsCommonModuleName        DisplayString,
            cpqHeOsCommonModuleVersion     DisplayString,
            cpqHeOsCommonModuleDate        OCTET STRING,
            cpqHeOsCommonModulePurpose     DisplayString
        }

    cpqHeOsCommonModuleIndex OBJECT-TYPE
        SYNTAX  INTEGER (0..255)
        ACCESS  read-only
        STATUS  deprecated
        DESCRIPTION
            "A unique index for this module description."
        ::= { cpqHeOsCommonModuleEntry 1 }

    cpqHeOsCommonModuleName OBJECT-TYPE
        SYNTAX  DisplayString (SIZE (0..255))
        ACCESS  read-only
        STATUS  deprecated
        DESCRIPTION
            "The module name."
        ::= { cpqHeOsCommonModuleEntry 2 }

    cpqHeOsCommonModuleVersion OBJECT-TYPE
        SYNTAX  DisplayString (SIZE (0..5))
        ACCESS  read-only
        STATUS  deprecated
        DESCRIPTION
            "The module version in XX.YY format.

            Where XX is the major version number and YY is the minor version
            number.  This field will be null (size 0) string if the agent
            cannot provide the module version."
        ::= { cpqHeOsCommonModuleEntry 3 }

    cpqHeOsCommonModuleDate OBJECT-TYPE
        SYNTAX  OCTET STRING (SIZE (7))
        ACCESS  read-only
        STATUS  deprecated
        DESCRIPTION
            "The module date.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant.  The year field is set
            with the most significant octet first."
        ::= { cpqHeOsCommonModuleEntry 4 }

    cpqHeOsCommonModulePurpose OBJECT-TYPE
        SYNTAX  DisplayString (SIZE (0..255))
        ACCESS  read-only
        STATUS  deprecated
        DESCRIPTION
            "The purpose of the module described in this entry."
        ::= { cpqHeOsCommonModuleEntry 5 }

-- ****************************************************************************
--   Health MIB Critical Error Group
--   ===============================
--
-- The compaq enterprise               (1.3.6.1.4.1.232)
--      cpqHealth Group                (1.3.6.1.4.1.232.6)
--       cpqHeComponent Group          (1.3.6.1.4.1.232.6.2)
--        cpqHeCriticalError Group     (1.3.6.1.4.1.232.6.2.2)
--
--  The cpqHeCriticalError group describes the health critical error log.
--
--  Implementation of the cpqHeCriticalError group is mandatory for all
--  agents that support the Server Health MIB.
--
-- ****************************************************************************

    cpqHeCritLogSupported OBJECT-TYPE
        SYNTAX  INTEGER {
            other(1),
            notSupported(2),
            supported(3)
            }
        ACCESS  read-only
        STATUS  mandatory
        DESCRIPTION
            "This value specifies if this system supports the critical
            error logging feature."
        ::= { cpqHeCriticalError 1 }

    cpqHeCritLogCondition OBJECT-TYPE
        SYNTAX  INTEGER {
            other(1),
            ok(2),
            degraded(3),
            failed(4)
            }
        ACCESS  read-only
        STATUS  mandatory
        DESCRIPTION
            "This value specifies the overall condition of the critical
            error log feature."
        ::= { cpqHeCriticalError 2 }

    cpqHeLastCritErrorAbendMsg OBJECT-TYPE
        SYNTAX  DisplayString (SIZE (0..255))
        ACCESS  read-only
        STATUS  mandatory
        DESCRIPTION
            "Last Critical Termination message.

             The message associated with the last critical error of
             type criticalException(14) or abend(27)."
        ::= { cpqHeCriticalError 3 }

-- ****************************************************************************
--   Health MIB Critical Error Table
--   ===============================
--
-- The compaq enterprise               (1.3.6.1.4.1.232)
--      cpqHealth Group                (1.3.6.1.4.1.232.6)
--       cpqHeComponent Group          (1.3.6.1.4.1.232.6.2)
--        cpqHeCriticalError Group     (1.3.6.1.4.1.232.6.2.2)
--         cpqHeCriticalErrorTable     (1.3.6.1.4.1.232.6.2.2.4)
--
-- ****************************************************************************

    cpqHeCriticalErrorTable OBJECT-TYPE
        SYNTAX  SEQUENCE OF CpqHeCriticalErrorEntry
        ACCESS  not-accessible
        STATUS  mandatory
        DESCRIPTION
            "A table of critical error descriptions."
        ::= { cpqHeCriticalError 4 }

    cpqHeCriticalErrorEntry OBJECT-TYPE
        SYNTAX  CpqHeCriticalErrorEntry
        ACCESS  not-accessible
        STATUS  mandatory
        DESCRIPTION
            "A critical error description."
        INDEX   { cpqHeCriticalErrorIndex }
        ::= { cpqHeCriticalErrorTable 1 }

    CpqHeCriticalErrorEntry ::= SEQUENCE {
        cpqHeCriticalErrorIndex          INTEGER,
        cpqHeCriticalErrorStatus         INTEGER,
        cpqHeCriticalErrorType           INTEGER,
        cpqHeCriticalErrorTime           OCTET STRING,
        cpqHeCriticalErrorInfo           OCTET STRING,
        cpqHeCriticalErrorDesc           DisplayString
    }

    cpqHeCriticalErrorIndex OBJECT-TYPE
        SYNTAX  INTEGER (0..65535)
        ACCESS  read-only
        STATUS  mandatory
        DESCRIPTION
            "A number that uniquely specifies this critical error 
            description.  The entries will be in order of occurrence
            with the most recent entry first."
        ::= { cpqHeCriticalErrorEntry 1 }

    cpqHeCriticalErrorStatus OBJECT-TYPE
        SYNTAX  INTEGER {
            uncorrected(1),
            corrected(2)
            }
        ACCESS  read-write
        STATUS  mandatory
        DESCRIPTION
            "This value specifies if the user has marked this error as
            corrected.  Marking errors as corrected may be performed with
            the Diagnostics or by a set operation on this variable.
            Attempting to set this variable to uncorrected(1) will fail."
        ::= { cpqHeCriticalErrorEntry 2 }

    cpqHeCriticalErrorType OBJECT-TYPE
        SYNTAX  INTEGER {
            other(1),
            empty(2),
            nonCorrectableMemErr(3),
            busMasterTimeoutNmi(4),
            commandBusTimeoutNmi(5),
            ioCheckNmi(6),
            refreshOverflowNmi(7),
            cacheParityNmi(8),
            processorParityNmi(9),
            eisaHostMemReadHit(10),
            processorFailure(11),
            cautionTemperature(12),
            postCriticalError(13),
            criticalException(14),
            serverManagerIfFail(15),
            pentiumIperr(16),
            pentiumAperr(17),
            pentiumIeerr(18),
            pentiumApcheck(19),
            cpuLocalError(20),
            failsafeTimer(21),
            softwareNmi(22),
            asrBaseMemoryParity(23),
            asrExtendedMemParity(24),
            asrResetLimit(25),
            asrMemoryParity(26),
            abend(27),
            asrTestEvent(28),
            asrTimeoutNmi(29),
            fanFailure(30),
            upsDetectedLineFail(31),
            asrDetectedAtBoot(32),
            redunPowerSupplyFailure(33),
            pciBusParityError(34),
            diagnosticError(35),
            rtcChipBatteryFailure(36),
            pentiumBerr(37),
            dcConverterFailure(38),
            cpuInternalThreshPassed(39)
            }
        ACCESS  read-only
        STATUS  mandatory
        DESCRIPTION
            "This value specifies the type of error."
        ::= { cpqHeCriticalErrorEntry 3 }

    cpqHeCriticalErrorTime OBJECT-TYPE
        SYNTAX  OCTET STRING (SIZE (0..3))
        ACCESS  read-only
        STATUS  mandatory
        DESCRIPTION
            "The time of the error: hour (first five bits), day of month
            (next 5 bits), month (next 4 bits), year of the current century
            (next 7 bits).  The last 3 bits are reserved."
        ::= { cpqHeCriticalErrorEntry 4 }

    cpqHeCriticalErrorInfo OBJECT-TYPE
        SYNTAX  OCTET STRING (SIZE (0..4))
        ACCESS  read-only
        STATUS  mandatory
        DESCRIPTION
            "Information about the error."
        ::= { cpqHeCriticalErrorEntry 5 }

    cpqHeCriticalErrorDesc OBJECT-TYPE
        SYNTAX  DisplayString (SIZE (0..255))
        ACCESS  read-only
        STATUS  mandatory
        DESCRIPTION
            "A text description of the critical error."
        ::= { cpqHeCriticalErrorEntry 6 }

-- ****************************************************************************
--   Health MIB Correctable Memory Error Group
--   =========================================
--
-- The compaq enterprise               (1.3.6.1.4.1.232)
--      cpqHealth Group                (1.3.6.1.4.1.232.6)
--       cpqHeComponent Group          (1.3.6.1.4.1.232.6.2)
--        cpqHeCorrectableMemory Group (1.3.6.1.4.1.232.6.2.3)
--
--  The cpqHeCorrectableMemory group describes the health correctable memory
--  error log.
--
--  Implementation of the cpqHeCorrectableMemory group is mandatory for all
--  agents that support the Server Health MIB on a system that has the
--  correctable memory feature.
--
-- ****************************************************************************

    cpqHeCorrMemLogStatus OBJECT-TYPE
        SYNTAX  INTEGER {
            other(1),
            notSupported(2),
            disabled(3),
            enabled(4)
            }
        ACCESS  read-only
        STATUS  mandatory
        DESCRIPTION
            "This value specifies whether this system is currently tracking
            correctable memory errors."
        ::= { cpqHeCorrectableMemory 1 }

    cpqHeCorrMemLogCondition OBJECT-TYPE
        SYNTAX  INTEGER {
            other(1),
            ok(2),
            degraded(3),
            failed(4)
            }
        ACCESS  read-only
        STATUS  mandatory
        DESCRIPTION
            "This value specifies the overall condition of the correctable
            memory error log feature."
        ::= { cpqHeCorrectableMemory 2 }

    cpqHeCorrMemTotalErrs OBJECT-TYPE
        SYNTAX  INTEGER (0..2147483647)
        ACCESS  read-only
        STATUS  deprecated
        DESCRIPTION
            "The number of correctable memory errors that have occurred."
        ::= { cpqHeCorrectableMemory 3 }

-- ****************************************************************************
--   Health MIB Correctable Memory Error Table
--   =========================================
--
-- The compaq enterprise               (1.3.6.1.4.1.232)
--      cpqHealth Group                (1.3.6.1.4.1.232.6)
--       cpqHeComponent Group          (1.3.6.1.4.1.232.6.2)
--        cpqHeCorrectableMemory Group (1.3.6.1.4.1.232.6.2.3)
--         cpqHeCorrMemErrTable        (1.3.6.1.4.1.232.6.2.3.4)
--
-- ****************************************************************************

    cpqHeCorrMemErrTable OBJECT-TYPE
        SYNTAX  SEQUENCE OF CpqHeCorrMemErrEntry
        ACCESS  not-accessible
        STATUS  mandatory
        DESCRIPTION
            "A table of correctable memory error descriptions."
        ::= { cpqHeCorrectableMemory 4 }

    cpqHeCorrMemErrEntry OBJECT-TYPE
        SYNTAX  CpqHeCorrMemErrEntry
        ACCESS  not-accessible
        STATUS  mandatory
        DESCRIPTION
            "A correctable memory error description."
        INDEX   { cpqHeCorrMemErrIndex }
        ::= { cpqHeCorrMemErrTable 1 }

    CpqHeCorrMemErrEntry ::= SEQUENCE {
        cpqHeCorrMemErrIndex       INTEGER,
        cpqHeCorrMemErrCount       INTEGER,
        cpqHeCorrMemErrTime        OCTET STRING,
        cpqHeCorrMemErrDdr         OCTET STRING,
        cpqHeCorrMemErrSyndrome    OCTET STRING,
        cpqHeCorrMemErrDesc        DisplayString,
        cpqHeCorrMemErrHwLocation  DisplayString
    }

    cpqHeCorrMemErrIndex OBJECT-TYPE
        SYNTAX  INTEGER (0..65535)
        ACCESS  read-only
        STATUS  mandatory
        DESCRIPTION
            "A number that uniquely specifies this correctable memory error
            description.  The entries will be in order of occurrence with the
            most recent new entry first."
        ::= { cpqHeCorrMemErrEntry 1 }

    cpqHeCorrMemErrCount OBJECT-TYPE
        SYNTAX  INTEGER (0..255)
        ACCESS  read-write
        STATUS  mandatory
        DESCRIPTION
            "The number of times this memory location has had a correctable
            memory error.  The value zero (0) indicates that the user has
            marked this error as corrected.  Marking errors as corrected may
            be performed with the Diagnostics or with a set operation
            of 0 on this variable.  Any non-zero valued set operation will
            fail."
        ::= { cpqHeCorrMemErrEntry 2 }

    cpqHeCorrMemErrTime OBJECT-TYPE
        SYNTAX  OCTET STRING (SIZE (0..3))
        ACCESS  read-only
        STATUS  mandatory
        DESCRIPTION
            "The time of the error: hour (first five bits), day of month
            (next 5 bits), month (next 4 bits), year of the current century
            (next 7 bits).  The last 3 bits are reserved."
        ::= { cpqHeCorrMemErrEntry 3 }

    cpqHeCorrMemErrDdr OBJECT-TYPE
        SYNTAX  OCTET STRING (SIZE (0..2))
        ACCESS  read-only
        STATUS  mandatory
        DESCRIPTION
            "The data destination register value.

            This contains information about the memory bank in which the
            error occurred.  The interpretation of this value is dependent
            on the machine type."
        ::= { cpqHeCorrMemErrEntry 4 }

    cpqHeCorrMemErrSyndrome OBJECT-TYPE
        SYNTAX  OCTET STRING (SIZE (0..2))
        ACCESS  read-only
        STATUS  mandatory
        DESCRIPTION
            "The memory syndrome value.

            This contains information about the memory module in which the
            error occurred.  The interpretation of this value is dependant
            on the machine type."
        ::= { cpqHeCorrMemErrEntry 5 }

    cpqHeCorrMemErrDesc OBJECT-TYPE
        SYNTAX  DisplayString (SIZE (0..255))
        ACCESS  read-only
        STATUS  mandatory
        DESCRIPTION
            "A text description of the correctable memory error."
        ::= { cpqHeCorrMemErrEntry 6 }

    cpqHeCorrMemErrHwLocation  OBJECT-TYPE
        SYNTAX  DisplayString (SIZE (0..255))
        ACCESS  read-only
        STATUS  optional
        DESCRIPTION
            "A text description of the hardware location, on complex
             multi SBB hardware only, for the correctable memory error.
             A NULL string indicates that the hardware location could not
             be determined or is irrelevant."
        ::= { cpqHeCorrMemErrEntry 7 }

    cpqHeCorrMemErrorCntThresh OBJECT-TYPE
        SYNTAX  INTEGER (0..2147483647)
        ACCESS  read-only
        STATUS  mandatory
        DESCRIPTION
            "The error threshold for Correctable memory errors. When
            cpqHeCorrMemErrCount is greater than or equal to this value
            user action is required to replace the failing memory module."
        ::= { cpqHeCorrectableMemory 5 }

-- ****************************************************************************
--   Health MIB Automatic Server Recovery (ASR) Group
--   ================================================
--
-- The compaq enterprise               (1.3.6.1.4.1.232)
--      cpqHealth Group                (1.3.6.1.4.1.232.6)
--       cpqHeComponent Group          (1.3.6.1.4.1.232.6.2)
--        cpqHeAsr Group               (1.3.6.1.4.1.232.6.2.5)
--
--  The cpqHeAsr group describes the Automatic Server Recovery Health
--  feature.
--
--  Implementation of the cpqHeAsr group is mandatory for all agents that
--  support the Server Health MIB on a system that supports the ASR feature.
--
-- ****************************************************************************

    cpqHeAsrStatus OBJECT-TYPE
        SYNTAX  INTEGER {
            other(1),
            notAvailable(2),
            disabled(3),
            enabled(4)
            }
        ACCESS  read-write
        STATUS  mandatory
        DESCRIPTION
            "The Automatic Server Recovery feature status.

            If this object is currently other(1) or notAvailable(2) all
            set operations will fail.  Any attempt to set this object to
            other(1) or notAvailable(2) by a management station will fail.

            Setting this object to disabled(3) or enabled(4) will disable
            or enable the ASR feature.

            Setting this object to disabled(3) will disable the following
            objects:
                cpqHeAsrPagerStatus
                cpqHeAsrDialInStatus
                cpqHeAsrDialOutStatus"
        ::= { cpqHeAsr 1 }

    cpqHeAsrMajorVersion OBJECT-TYPE
        SYNTAX  INTEGER (0..255)
        ACCESS  read-only
        STATUS  mandatory
        DESCRIPTION
            "The major version number of the Automatic Server Recovery
            feature hardware."
        ::= { cpqHeAsr 2 }

    cpqHeAsrMinorVersion OBJECT-TYPE
        SYNTAX  INTEGER (0..255)
        ACCESS  read-only
        STATUS  mandatory
        DESCRIPTION
            "The minor version number of the Automatic Server Recovery
            feature hardware."
        ::= { cpqHeAsr 3 }

    cpqHeAsrTimeout OBJECT-TYPE
        SYNTAX  INTEGER
        ACCESS  read-write
        STATUS  mandatory
        DESCRIPTION
            "The time-out in minutes for the Automatic Server Recovery
            feature hardware.  If the variable is not supported, a value
            of -1 will be returned."
        ::= { cpqHeAsr 4 }

    cpqHeAsrBaseIo OBJECT-TYPE
        SYNTAX  INTEGER
        ACCESS  read-only
        STATUS  mandatory
        DESCRIPTION
            "The Automatic Server Recovery feature Base I/O address."
        ::= { cpqHeAsr 5 }

    cpqHeAsrPost OBJECT-TYPE
        SYNTAX  INTEGER {
            other(1),
            failed(2),
            ok(3)
            }
        ACCESS  read-only
        STATUS  deprecated
        DESCRIPTION
            "Indicates if the Automatic Server Recovery timer passed
             the server power-on self test."
        ::= { cpqHeAsr 6 }

    cpqHeAsrReset OBJECT-TYPE
        SYNTAX  INTEGER {
            other(1),
            manualReset(2),
            asrReset(3),
            viewed-asrReset(4)
            }
        ACCESS  read-write
        STATUS  mandatory
        DESCRIPTION
            "Indicates if the previous reset was caused by the ASR
             timer. An asrReset(3) condition may be changed with a
             viewed-asrReset(4) set operation.  This is only valid
             if this variable's current value is asrReset(3).  Setting
             this variable to any other value than viewed-asrReset(4)
             will fail."
        ::= { cpqHeAsr 7 }

    cpqHeAsrReboot OBJECT-TYPE
        SYNTAX  INTEGER {
            other(1),
            bootOs(2),
            bootUtilities(3)
            }
        ACCESS  read-write
        STATUS  mandatory
        DESCRIPTION
            "Indicates what software should be started when the server is
             rebooted by the ASR feature.

             If this object is currently set to other(1), set operations
             will fail.  This object may not be set to other(1) by a
             management station.

             Setting this object to bootOs(2) or bootUtilities(3)
             will select the software to be started after an ASR reboot."
        ::= { cpqHeAsr 8 }

    cpqHeAsrRebootLimit OBJECT-TYPE
        SYNTAX  INTEGER 
        ACCESS  read-write
        STATUS  mandatory
        DESCRIPTION
            "The number of ASR timer reboots that should cause the server to
            boot the firmware console and override the standard reboot
            setting (cpqHeAsrReboot).  If this value is 0 then no limit is
            defined and the standard reboot option will always be used.  If
            the variable is not supported, a value of -1 will be returned."
        ::= { cpqHeAsr 9 }

    cpqHeAsrRebootCount OBJECT-TYPE
        SYNTAX  INTEGER
        ACCESS  read-write
        STATUS  mandatory
        DESCRIPTION
            "The number of ASR reboots that have occurred on this server
             since the last manual reboot. Reboot count may be reset with
             a zero valued set operation on this variable. Setting this
             value to a non-zero value will fail.  If the variable is not
             supported, a value of -1 will be returned."
        ::= { cpqHeAsr 10 }

    cpqHeAsrPagerStatus OBJECT-TYPE
        SYNTAX  INTEGER {
            other(1),
            disabled(2),
            enabled(3)
            }
        ACCESS  read-write
        STATUS  mandatory
        DESCRIPTION
            "The status of the ASR pager feature.

            If the current value of this object is not other(1), it may
            be set to disabled(2) or enabled(3).  Attempting a set operation
            while the value is other(1) will fail.  Attempting to set the
            value to other(1) will fail.

            Setting this object to enabled(3) will enable the
            cpqHeAsrStatus object."
        ::= { cpqHeAsr 11 }

    cpqHeAsrPagerNumber OBJECT-TYPE
        SYNTAX  DisplayString (SIZE (0..60))
        ACCESS  read-write
        STATUS  mandatory
        DESCRIPTION
            "The pager number to be dialed after an ASR reboot."
        ::= { cpqHeAsr 12 }

    cpqHeAsrCommPort OBJECT-TYPE
        SYNTAX  INTEGER
        ACCESS  read-write
        STATUS  mandatory
        DESCRIPTION
            "The communication port to be used by the firmware pager and
            console.  The value zero (0) indicates this setting is undefined.

            If the current value of this object is zero (0) any
            attempt to set this object from a management station
            will fail.  Any attempt to set this object to zero (0)
            by a management station will fail.  If the variable is not
            supported, a value of -1 will be returned."
        ::= { cpqHeAsr 13 }

    cpqHeAsrBaudRate OBJECT-TYPE
        SYNTAX  INTEGER
        ACCESS  read-only
        STATUS  mandatory
        DESCRIPTION
            "The baud rate to be used by the firmware pager and console.
            The value zero (0) indicates this setting is undefined.  If the 
            variable is not supported, a value of -1 will be returned."
        ::= { cpqHeAsr 14 }

    cpqHeAsrPagerMessage OBJECT-TYPE
        SYNTAX  DisplayString (SIZE (0..8))
        ACCESS  read-write
        STATUS  mandatory
        DESCRIPTION
            "The 8 character pager message entered by the user."
        ::= { cpqHeAsr 15 }

    cpqHeAsrBootFail OBJECT-TYPE
        SYNTAX  INTEGER {
            other(1),
            interrupt18(2)
            }
        ACCESS  read-only
        STATUS  deprecated
        DESCRIPTION
            "The action to be taken if an ASR reboot failure occurs."
        ::= { cpqHeAsr 16 }

    cpqHeAsrCondition OBJECT-TYPE
        SYNTAX  INTEGER {
            other(1),
            ok(2),
            degraded(3),
            failed(4)
            }
        ACCESS  read-only
        STATUS  mandatory
        DESCRIPTION
            "This value specifies the overall condition of the ASR feature."
        ::= { cpqHeAsr 17 }

    cpqHeAsrDialInStatus OBJECT-TYPE
        SYNTAX  INTEGER {
            other(1),
            disabled(2),
            enabled(3)
            }
        ACCESS  read-write
        STATUS  mandatory
        DESCRIPTION
            "The status of the ASR dial in feature.

            If the current value of this object is other(1) any attempt to
            set this object from a management station will fail.  Any
            attempt to set this object to other(1) by a management station
            will fail.

            Setting this object to enabled(3) will enable the
            cpqHeAsrStatus object."
        ::= { cpqHeAsr 18 }

    cpqHeAsrDialOutStatus OBJECT-TYPE
        SYNTAX  INTEGER {
            other(1),
            disabled(2),
            enabled(3)
            }
        ACCESS  read-write
        STATUS  mandatory
        DESCRIPTION
            "The status of the ASR dial out feature.

            If the current value of this object is other(1) any attempt to
            set this object from a management station will fail.  Any
            attempt to set this object to other(1) by a management station
            will fail.

            Setting this object to enabled(3) will enable the
            cpqHeAsrStatus and the cpqHeAsrDialInStatus objects."
        ::= { cpqHeAsr 19 }

    cpqHeAsrDialOutNumber OBJECT-TYPE
        SYNTAX  DisplayString (SIZE (0..60))
        ACCESS  read-write
        STATUS  mandatory
        DESCRIPTION
            "The phone number to be dialed for remote diagnostics if an ASR
            reset occurs."
        ::= { cpqHeAsr 20 }

    cpqHeAsrNetworkAccessStatus OBJECT-TYPE
        SYNTAX  INTEGER {
            other(1),
            disabled(2),
            enabled(3)
            }
        ACCESS  read-write
        STATUS  mandatory
        DESCRIPTION
            "The status of the ASR network access feature.

            If the current value of this object is other(1) any attempt to
            set this object from a management station will fail.  Any
            attempt to set this object to other(1) by a management station
            will fail."
        ::= { cpqHeAsr 21 }

    cpqHeAsrPollTime OBJECT-TYPE
        SYNTAX  INTEGER
        ACCESS  read-write
        STATUS  optional
        DESCRIPTION
            "The poll time in seconds the ASR watchdog timer is being
             refreshed periodically."
        ::= { cpqHeAsr 22 }


-- ****************************************************************************
--   Health MIB Thermal Group
--   ========================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--
--  The cpqHeThermal group describes the status of the temperature and the
--  fans that regulate the temperature.
--
--  Implementation of the cpqHeThermal group is mandatory for all agents
--  that support the Server Health MIB on a system that supports the thermal
--  sensing features.
--
-- ****************************************************************************

    cpqHeThermalCondition OBJECT-TYPE
        SYNTAX  INTEGER {
            other(1),
            ok(2),
            degraded(3),
            failed(4)
            }
        ACCESS  read-only
        STATUS  mandatory
        DESCRIPTION
            "This value specifies the overall condition of the system's
            thermal environment."
        ::= { cpqHeThermal 1 }

    cpqHeThermalDegradedAction OBJECT-TYPE
        SYNTAX  INTEGER {
            other(1),
            continue(2),
            shutdown(3)
            }
        ACCESS  read-write
        STATUS  mandatory
        DESCRIPTION
            "The action to perform when the thermal condition is degraded.

            This value will be one of the following:
            other(1)
              This feature is not supported by this system or driver.

            continue(2)
              The system should be allowed to continue.

            shutdown(3)
              The system should be shutdown."
        ::= { cpqHeThermal 2 }

    cpqHeThermalTempStatus OBJECT-TYPE
        SYNTAX  INTEGER {
            other(1),
            ok(2),
            degraded(3),
            failed(4)
            }
        ACCESS  read-only
        STATUS  mandatory
        DESCRIPTION
            "The status of the system's temperature sensors:

            This value will be one of the following:
            other(1)
              Temp sensing is not supported by this system or driver.

            ok(2)
              All temp sensors are within normal operating range.

            degraded(3)
              A temp sensor is outside of normal operating range.

            failed(4)
              A temp sensor detects a condition that could permanently
              damage the system.

            The system will automatically shutdown if the failed(4) condition
            results, so it is unlikely that this value will ever be returned
            by the agent.  If the cpqHeThermalDegradedAction is set to
            shutdown(3) the system will be shutdown if the degraded(3)
            condition occurs."
        ::= { cpqHeThermal 3 }

    cpqHeThermalSystemFanStatus OBJECT-TYPE
        SYNTAX  INTEGER {
            other(1),
            ok(2),
            degraded(3),
            failed(4)
            }
        ACCESS  read-only
        STATUS  mandatory
        DESCRIPTION
            "The status of the fan(s) in the system.

            This value will be one of the following:
            other(1)
              Fan status detection is not supported by this system or driver.

            ok(2)
              All fans are operating properly.

            degraded(3)
              A non-required fan is not operating properly.

            failed(4)
              A required fan is not operating properly.

            If the cpqHeThermalDegradedAction is set to shutdown(3) the
            system will be shutdown if the failed(4) condition occurs."
        ::= { cpqHeThermal 4 }

    cpqHeThermalCpuFanStatus OBJECT-TYPE
        SYNTAX  INTEGER {
            other(1),
            ok(2),
            failed(4)
            }
        ACCESS  read-only
        STATUS  mandatory
        DESCRIPTION
            "The status of the processor fan(s) in the system.

            This value will be one of the following:
            other(1)
              Fan status detection is not supported by this system or driver.

            ok(2)
              All fans are operating properly.

            failed(4)
              A fan is not operating properly.

            The system will be shutdown if the failed(4) condition occurs."
        ::= { cpqHeThermal 5 }

-- ****************************************************************************
--   Health MIB Thermal Fan Table
--   ============================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--         cpqHeThermalFanTable        (1.3.6.1.4.1.232.6.2.6.6)
--
-- ****************************************************************************

    cpqHeThermalFanTable OBJECT-TYPE
        SYNTAX  SEQUENCE OF CpqHeThermalFanEntry
        ACCESS  not-accessible
        STATUS  mandatory
        DESCRIPTION
            "A table of fan descriptions."
        ::= { cpqHeThermal 6 }

    cpqHeThermalFanEntry OBJECT-TYPE
        SYNTAX  CpqHeThermalFanEntry
        ACCESS  not-accessible
        STATUS  mandatory
        DESCRIPTION
            "A fan description."
        INDEX   { cpqHeThermalFanIndex }
        ::= { cpqHeThermalFanTable 1 }

    CpqHeThermalFanEntry ::= SEQUENCE {
        cpqHeThermalFanIndex       INTEGER,
        cpqHeThermalFanRequired    INTEGER,
        cpqHeThermalFanPresent     INTEGER,
        cpqHeThermalFanCpuFan      INTEGER,
        cpqHeThermalFanStatus      INTEGER,
        cpqHeThermalFanHwLocation  DisplayString,
        cpqHeThermalFanCurrentSpeed INTEGER
    }

    cpqHeThermalFanIndex OBJECT-TYPE
        SYNTAX  INTEGER (0..8)
        ACCESS  read-only
        STATUS  mandatory
        DESCRIPTION
            "A number that uniquely specifies this fan description."
        ::= { cpqHeThermalFanEntry 1 }

    cpqHeThermalFanRequired OBJECT-TYPE
        SYNTAX  INTEGER {
            other(1),
            nonRequired(2),
            required(3)
            }
        ACCESS  read-only
        STATUS  mandatory
        DESCRIPTION
            "This specifies if the fan described is required for proper
            operation of the system."
        ::= { cpqHeThermalFanEntry 2 }

    cpqHeThermalFanPresent OBJECT-TYPE
        SYNTAX  INTEGER {
            other(1),
            absent(2),
            present(3)
            }
        ACCESS  read-only
        STATUS  mandatory
        DESCRIPTION
            "This specifies if the fan described is present in the system."
        ::= { cpqHeThermalFanEntry 3 }

    cpqHeThermalFanCpuFan OBJECT-TYPE
        SYNTAX  INTEGER {
            other(1),
            systemFan(2),
            cpuFan(3)
            }
        ACCESS  read-only
        STATUS  mandatory
        DESCRIPTION
            "This specifies if the described fan is intended specifically
             to cool the CPU(s)."
        ::= { cpqHeThermalFanEntry 4 }

    cpqHeThermalFanStatus OBJECT-TYPE
        SYNTAX  INTEGER {
            other(1),
            ok(2),
            failed(4)
            }
        ACCESS  read-only
        STATUS  mandatory
        DESCRIPTION
            "This specifies if the fan described is operating properly.

            This value will be one of the following:
            other(1)
              Fan status detection is not supported by this system or driver.

            ok(2)
              The fan is operating properly.

            failed(4)
              The fan is not operating properly."
        ::= { cpqHeThermalFanEntry 5 }

    cpqHeThermalFanHwLocation  OBJECT-TYPE
        SYNTAX  DisplayString (SIZE (0..255))
        ACCESS  read-only
        STATUS  optional
        DESCRIPTION
            "A text description of the hardware location, on complex
             multi SBB hardware only, for the fan.
             A NULL string indicates that the hardware location could not
             be determined or is irrelevant."
        ::= { cpqHeThermalFanEntry 6 }

    cpqHeThermalFanCurrentSpeed  OBJECT-TYPE
        SYNTAX  INTEGER
        ACCESS  read-only
        STATUS  optional
        DESCRIPTION
            "The current speed of a fan in rpm - revolutions per minute."
        ::= { cpqHeThermalFanEntry 7 }


-- ****************************************************************************
--   Health MIB Fault Tolerant Fan Table
--   ===================================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--         cpqHeFltTolFanTable         (1.3.6.1.4.1.232.6.2.6.7)
--
-- ****************************************************************************

    cpqHeFltTolFanTable OBJECT-TYPE
        SYNTAX  SEQUENCE OF CpqHeFltTolFanEntry
        ACCESS  not-accessible
        STATUS  mandatory
        DESCRIPTION
            "A table of Fault Tolerant Fan Entries."
        ::= { cpqHeThermal 7 }

    cpqHeFltTolFanEntry OBJECT-TYPE
        SYNTAX  CpqHeFltTolFanEntry
        ACCESS  not-accessible
        STATUS  mandatory
        DESCRIPTION
            "A Fault Tolerant Fan Entry."
        INDEX   { cpqHeFltTolFanChassis, cpqHeFltTolFanIndex }
        ::= { cpqHeFltTolFanTable 1 }

    CpqHeFltTolFanEntry ::= SEQUENCE {
        cpqHeFltTolFanChassis                   INTEGER,
        cpqHeFltTolFanIndex                     INTEGER,
        cpqHeFltTolFanLocale                    INTEGER,
        cpqHeFltTolFanPresent                   INTEGER,
        cpqHeFltTolFanType                      INTEGER,
        cpqHeFltTolFanSpeed                     INTEGER,
        cpqHeFltTolFanRedundant                 INTEGER,
        cpqHeFltTolFanRedundantPartner          INTEGER,
        cpqHeFltTolFanCondition                 INTEGER,
        cpqHeFltTolFanHotPlug                   INTEGER,
        cpqHeFltTolFanHwLocation                DisplayString,
        cpqHeFltTolFanCurrentSpeed              INTEGER
    }

    cpqHeFltTolFanChassis OBJECT-TYPE
        SYNTAX  INTEGER
        ACCESS  read-only
        STATUS  mandatory
        DESCRIPTION
            "The System Chassis number."
        ::= { cpqHeFltTolFanEntry 1 }

    cpqHeFltTolFanIndex OBJECT-TYPE
        SYNTAX  INTEGER
        ACCESS  read-only
        STATUS  mandatory
        DESCRIPTION
            "A number that uniquely specifies this fan description."
        ::= { cpqHeFltTolFanEntry 2 }

    cpqHeFltTolFanLocale OBJECT-TYPE
        SYNTAX  INTEGER {
            other(1),
            unknown(2),
            system(3),
            systemBoard(4),
            ioBoard(5),
            cpu(6),
            memory(7),
            storage(8),
            removableMedia(9),
            powerSupply(10),
            ambient(11),
            chassis(12),
            bridgeCard(13),
            managementBoard(14),
            backplane(15),
            networkSlot(16),
            bladeSlot(17),
            virtual(18)
            }
        ACCESS  read-only
        STATUS  mandatory
        DESCRIPTION
            "This specifies the location of the fan in the system."
        ::= { cpqHeFltTolFanEntry 3 }

    cpqHeFltTolFanPresent OBJECT-TYPE
        SYNTAX  INTEGER {
            other(1),
            absent(2),
            present(3)
            }
        ACCESS  read-only
        STATUS  mandatory
        DESCRIPTION
            "This specifies if the fan described is present in the system."
        ::= { cpqHeFltTolFanEntry 4 }

    cpqHeFltTolFanType OBJECT-TYPE
        SYNTAX  INTEGER {
            other(1),
            tachOutput(2),
            spinDetect(3)
            }
        ACCESS  read-only
        STATUS  mandatory
        DESCRIPTION
            "This specifies the type of fan.

            other(1)
              The type of fan could not be determined.

            tachOutput(2)
              The fan can increase speed for greater cooling.  Implies
              spin detect.

            spinDetect(3)
              The fan can detect when the fan stops spinning."
        ::= { cpqHeFltTolFanEntry 5 }

    cpqHeFltTolFanSpeed OBJECT-TYPE
        SYNTAX  INTEGER {
            other(1),
            normal(2),
            high(3)
            }
        ACCESS  read-only
        STATUS  mandatory
        DESCRIPTION
            "This specifies the speed of the fan.  This value will be set
            if the fan type is tachOutput."
        ::= { cpqHeFltTolFanEntry 6 }

    cpqHeFltTolFanRedundant OBJECT-TYPE
        SYNTAX  INTEGER {
            other(1),
            notRedundant(2),
            redundant(3)
            }
        ACCESS  read-only
        STATUS  mandatory
        DESCRIPTION
            "This specifies if the fan is in a redundant configuration."
        ::= { cpqHeFltTolFanEntry 7 }

    cpqHeFltTolFanRedundantPartner OBJECT-TYPE
        SYNTAX  INTEGER
        ACCESS  read-only
        STATUS  mandatory
        DESCRIPTION
            "This specifies the index of the redundant partner.  A value
            of zero will be used if there is no redundant partner."
        ::= { cpqHeFltTolFanEntry 8 }

    cpqHeFltTolFanCondition OBJECT-TYPE
        SYNTAX  INTEGER {
            other(1),
            ok(2),
            degraded(3),
            failed(4)
            }
        ACCESS  read-only
        STATUS  mandatory
        DESCRIPTION
            "The condition of the fan.

            This value will be one of the following:
            other(1)
              Fan status detection is not supported by this system or driver.

            ok(2)
              The fan is operating properly.

            degraded(3)
              A redundant fan is not operating properly.

            failed(4)
              A non-redundant fan is not operating properly."
        ::= { cpqHeFltTolFanEntry 9 }
 
    cpqHeFltTolFanHotPlug OBJECT-TYPE
        SYNTAX  INTEGER {
            other(1),
            nonHotPluggable(2),
            hotPluggable(3)
            }
        ACCESS  read-only
        STATUS  mandatory
        DESCRIPTION
            "This indicates if the fan is capable of being removed and/or
            inserted while the system is in an operational state.

            If the value is hotPluggable(3), the fan can be safely
            removed if and only if the cpqHeFltTolFanRedundant
            field is in a redundant(3) state.

            This value will be one of the following:
            other(1)
              The state could not be determined.

            nonHotPluggable(2)
              The fan is not hot plug capable.

            hotPluggable(3)
              The fan is hot plug capable and can be removed if
              the system is operating in a redundant state.  A fan
              may be added to an empty fan bay."
        ::= { cpqHeFltTolFanEntry 10 }

    cpqHeFltTolFanHwLocation OBJECT-TYPE
        SYNTAX  DisplayString (SIZE (0..255))
        ACCESS  read-only
        STATUS  optional
        DESCRIPTION
            "A text description of the hardware location, on complex
             multi SBB hardware only, for the fan.
             A NULL string indicates that the hardware location could not
             be determined or is irrelevant."
        ::= { cpqHeFltTolFanEntry 11 }

    cpqHeFltTolFanCurrentSpeed OBJECT-TYPE
        SYNTAX  INTEGER
        ACCESS  read-only
        STATUS  optional
        DESCRIPTION
            "The current speed of a fan in rpm - revolutions per minute."
        ::= { cpqHeFltTolFanEntry 12 }


-- ****************************************************************************
--   Health MIB Temperature Sensor Table
--   ===================================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--         cpqHeTemperatureTable       (1.3.6.1.4.1.232.6.2.6.8)
--
-- ****************************************************************************

    cpqHeTemperatureTable OBJECT-TYPE
        SYNTAX  SEQUENCE OF CpqHeTemperatureEntry
        ACCESS  not-accessible
        STATUS  mandatory
        DESCRIPTION
            "A table of Temperature Sensor Entries."
        ::= { cpqHeThermal 8 }

    cpqHeTemperatureEntry OBJECT-TYPE
        SYNTAX  CpqHeTemperatureEntry
        ACCESS  not-accessible
        STATUS  mandatory
        DESCRIPTION
            "A Temperature Sensor Entry."
        INDEX   { cpqHeTemperatureChassis, cpqHeTemperatureIndex }
        ::= { cpqHeTemperatureTable 1 }

    CpqHeTemperatureEntry ::= SEQUENCE {
        cpqHeTemperatureChassis                   INTEGER,
        cpqHeTemperatureIndex                     INTEGER,
        cpqHeTemperatureLocale                    INTEGER,
        cpqHeTemperatureCelsius                   INTEGER,
        cpqHeTemperatureThreshold                 INTEGER,
        cpqHeTemperatureCondition                 INTEGER,
        cpqHeTemperatureThresholdType             INTEGER,
        cpqHeTemperatureHwLocation                DisplayString
    }

    cpqHeTemperatureChassis OBJECT-TYPE
        SYNTAX  INTEGER
        ACCESS  read-only
        STATUS  mandatory
        DESCRIPTION
            "The System Chassis number."
        ::= { cpqHeTemperatureEntry 1 }

    cpqHeTemperatureIndex OBJECT-TYPE
        SYNTAX  INTEGER
        ACCESS  read-only 
        STATUS  mandatory
        DESCRIPTION
            "A number that uniquely specifies this temperature sensor
            description."
        ::= { cpqHeTemperatureEntry 2 }

    cpqHeTemperatureLocale OBJECT-TYPE
        SYNTAX  INTEGER {
            other(1),
            unknown(2),
            system(3),
            systemBoard(4),
            ioBoard(5),
            cpu(6),
            memory(7),
            storage(8),
            removableMedia(9),
            powerSupply(10),
            ambient(11),
            chassis(12),
            bridgeCard(13)
            }
        ACCESS  read-only
        STATUS  mandatory
        DESCRIPTION
            "This specifies the location of the temperature sensor
            present in the system."
        ::= { cpqHeTemperatureEntry 3 }

    cpqHeTemperatureCelsius OBJECT-TYPE
        SYNTAX  INTEGER
        ACCESS  read-only
        STATUS  mandatory
        DESCRIPTION
            "This is the current temperature sensor reading in degrees
            celsius.

            If this value cannot be determined by software, then a value
            of -99 will be returned."
        ::= { cpqHeTemperatureEntry 4 }

    cpqHeTemperatureThreshold OBJECT-TYPE
        SYNTAX  INTEGER
        ACCESS  read-write
        STATUS  mandatory
        DESCRIPTION
            "This is the shutdown threshold temperature sensor setting
            in degrees celsius.  This is the temperature in which the
            sensor will be considered to be in a failed state thus
            causing the system to be shutdown.

            If this value cannot be determined by software, then a value
            of -99 will be returned.

            Only the Ambient zone type allows setting of the threshold
            temperature."
        ::= { cpqHeTemperatureEntry 5 }

    cpqHeTemperatureCondition OBJECT-TYPE
        SYNTAX  INTEGER {
            other(1),
            ok(2),
            degraded(3),
            failed(4)
            }
        ACCESS  read-only
        STATUS  mandatory
        DESCRIPTION
            "The Temperature sensor condition.

            This value will be one of the following:
            other(1)
              Temperature could not be determined.

            ok(2)
              The temperature sensor is within normal operating range.

            degraded(3)
              The temperature sensor is outside of normal operating range.

            failed(4)
              The temperature sensor detects a condition that could
              permanently damage the system.

            The system will automatically shutdown if the failed(4) condition
            results, so it is unlikely that this value will ever be returned
            by the agent.  If the cpqHeThermalDegradedAction is set to
            shutdown(3) the system will be shutdown if the degraded(3)
            condition occurs."
        ::= { cpqHeTemperatureEntry 6 }

    cpqHeTemperatureThresholdType OBJECT-TYPE
        SYNTAX  INTEGER {
            other(1),
            blowout(5),
            caution(9),
            critical(15),
            noreaction(16)
            }
        ACCESS  read-only
        STATUS  mandatory
        DESCRIPTION
            "This specifies the type of this instance of temperature
            sensor.

            This value will be one of the following:
            other(1)
              Temperature threshold type could not be determined.

            blowout(5)
              If a blowout(5) temperature sensor reaches its threshold,
              the fan or fans in the area of the temperature sensor will
              increase in speed in an attempt to reduce the temperature
              before a caution or critical threshold is reached.

            caution(9)
              If a caution(9) temperature sensor reaches its threshold,
              the cpqHeTemperatureCondition will be set to degraded(3)
              and the system will either continue or shutdown depending
              on the setting of cpqHeThermalDegradedAction.

            critical(15)
              If a critical(15) temperature sensor reaches its threshold,
              the cpqHeTemperatureCondition will be set to failed(4)
              and the system will shutdown.
              
            noreaction(16)
              this value will be defined when a threshold value is zero and 
              system will not react on those sensor as those threshold 
              sensors are meant for display purpose only."              

        ::= { cpqHeTemperatureEntry 7 }

    cpqHeTemperatureHwLocation OBJECT-TYPE
        SYNTAX  DisplayString (SIZE (0..255))
        ACCESS  read-only
        STATUS  optional
        DESCRIPTION
            "A text description of the hardware location, on complex
             multi SBB hardware only, for the temperature sensor.
             A NULL string indicates that the hardware location could not
             be determined or is irrelevant."
        ::= { cpqHeTemperatureEntry 8 }

-- ****************************************************************************
--   Health MIB Post Message Group
--   =============================
--
-- The compaq enterprise               (1.3.6.1.4.1.232)
--      cpqHealth Group                (1.3.6.1.4.1.232.6)
--       cpqHeComponent Group          (1.3.6.1.4.1.232.6.2)
--        cpqHePostMsg Group           (1.3.6.1.4.1.232.6.2.7)
--
--  The cpqHePostMsg group contains a table of the non-critical POST
--  errors that occurred during the last reboot.
--
--  Implementation of the cpqHePostMsg group is mandatory for all agents
--  that support the Server Health MIB on a system that supports the POST
--  error recording feature.
--
-- ****************************************************************************

    cpqHePostMsgCondition OBJECT-TYPE
        SYNTAX  INTEGER {
            other(1),
            ok(2),
            degraded(3),
            failed(4)
            }
        ACCESS  read-only
        STATUS  mandatory
        DESCRIPTION
            "This value specifies the overall condition of the POST
            error recording feature."
        ::= { cpqHePostMsg 1 }

-- ****************************************************************************
--   Health MIB Post Message Table
--   =============================
--
-- The compaq enterprise               (1.3.6.1.4.1.232)
--      cpqHealth Group                (1.3.6.1.4.1.232.6)
--       cpqHeComponent Group          (1.3.6.1.4.1.232.6.2)
--        cpqHePostMsg Group           (1.3.6.1.4.1.232.6.2.7)
--         cpqHePostMsgTable           (1.3.6.1.4.1.232.6.2.7.2)
--
--      This table may be empty if no errors occurred during POST.
--
-- ****************************************************************************

    cpqHePostMsgTable OBJECT-TYPE
        SYNTAX  SEQUENCE OF CpqHePostMsgEntry
        ACCESS  not-accessible
        STATUS  mandatory
        DESCRIPTION
            "A table of POST error message numbers."
        ::= { cpqHePostMsg 2 }

    cpqHePostMsgEntry OBJECT-TYPE
        SYNTAX  CpqHePostMsgEntry
        ACCESS  not-accessible
        STATUS  mandatory
        DESCRIPTION
            "A POST error message number."
        INDEX   { cpqHePostMsgIndex }
        ::= { cpqHePostMsgTable 1 }

    CpqHePostMsgEntry ::= SEQUENCE {
        cpqHePostMsgIndex       INTEGER,
        cpqHePostMsgCode        INTEGER,
        cpqHePostMsgDesc        DisplayString
    }


    cpqHePostMsgIndex OBJECT-TYPE
        SYNTAX  INTEGER (0..255)
        ACCESS  read-only
        STATUS  mandatory
        DESCRIPTION
            "A number that uniquely specifies this POST error description."
        ::= { cpqHePostMsgEntry 1 }

    cpqHePostMsgCode OBJECT-TYPE
        SYNTAX  INTEGER (0..255)
        ACCESS  read-only
        STATUS  mandatory
        DESCRIPTION
            "This specifies POST message number for this error."
        ::= { cpqHePostMsgEntry 2 }

    cpqHePostMsgDesc OBJECT-TYPE
         SYNTAX  DisplayString (SIZE (0..255))
         ACCESS  read-only
         STATUS  mandatory
         DESCRIPTION
             "This contains a text description of the POST error.
              A string of length zero (0) will be returned if no description
              is available."
         ::= { cpqHePostMsgEntry 3 }

    cpqHePostMsgEv OBJECT-TYPE
        SYNTAX  OCTET STRING (SIZE (0..8))
        ACCESS  read-write
        STATUS  mandatory
        DESCRIPTION
            "The EV used to store 8 non-critical POST error codes
             for use with Quicktest, Utilities, and CIM. Setting
             this variable with a zero length octet string will
             clear this variable.  All other set operations will
             fail."
        ::= { cpqHePostMsg 3 }


-- ****************************************************************************
--   Health MIB System Utilization Group
--   ===================================
--
-- The compaq enterprise               (1.3.6.1.4.1.232)
--      cpqHealth Group                (1.3.6.1.4.1.232.6)
--       cpqHeComponent Group          (1.3.6.1.4.1.232.6.2)
--        cpqHeSysUtil Group           (1.3.6.1.4.1.232.6.2.8)
--
--  The cpqHeSysUtil group contains measures of system utilization.
--  This group includes long term utilization information like the total
--  server up time since originally configured.  This group also contains
--  current operating utilization information such as the current EISA bus
--  utilization.
--
--  Implementation of the cpqHeSysUtil group is mandatory for all agents
--  that support the Server Health MIB on a system that supports any system
--  utilization features.
--
-- ****************************************************************************

    cpqHeSysUtilLifeTime OBJECT-TYPE
        SYNTAX  INTEGER (0..2147483647)
        ACCESS  read-only
        STATUS  mandatory
        DESCRIPTION
            "The total time (in minutes) the system has been in full
             operation (while the server health supporting software was
             running)."
        ::= { cpqHeSysUtil 1 }

    cpqHeSysUtilEisaBusMin OBJECT-TYPE
        SYNTAX  INTEGER
        ACCESS  read-only
        STATUS  mandatory
        DESCRIPTION
            "The EISA bus utilization as a percentage of the theoretical
            maximum during the last minute.  A value of -1 indicates that
            this feature is not supported on this machine or is not
            available."
        ::= { cpqHeSysUtil 2 }

    cpqHeSysUtilEisaBusFiveMin OBJECT-TYPE
        SYNTAX  INTEGER
        ACCESS  read-only
        STATUS  mandatory
        DESCRIPTION
            "The EISA bus utilization as a percentage of the theoretical
            maximum during the last five minutes.  A value of -1 indicates
            that this feature is not supported on this machine or is not
            available."
        ::= { cpqHeSysUtil 3 }

    cpqHeSysUtilEisaBusThirtyMin OBJECT-TYPE
        SYNTAX  INTEGER
        ACCESS  read-only
        STATUS  mandatory
        DESCRIPTION
            "The EISA bus utilization as a percentage of the theoretical
            maximum during the last thirty minutes.  A value of -1
            indicates that this feature is not supported on this machine
            or is not available."
        ::= { cpqHeSysUtil 4 }

    cpqHeSysUtilEisaBusHour OBJECT-TYPE
        SYNTAX  INTEGER
        ACCESS  read-only
        STATUS  mandatory
        DESCRIPTION
            "The EISA bus utilization as a percentage of the theoretical
            maximum during the last hour.  A value of -1 indicates that
            this feature is not supported on this machine or is not
            available."
        ::= { cpqHeSysUtil 5 }

-- ****************************************************************************
--   Health MIB PCI Utilization Table
--   ====================================
--
-- The compaq enterprise               (1.3.6.1.4.1.232)
--      cpqHealth Group                (1.3.6.1.4.1.232.6)
--       cpqHeComponent Group          (1.3.6.1.4.1.232.6.2)
--        cpqHeSysUtil Group           (1.3.6.1.4.1.232.6.2.8)
--         cpqHeSysUtilPciTable        (1.3.6.1.4.1.232.6.2.8.6)
--
--
-- ****************************************************************************

    cpqHeSysUtilPciTable OBJECT-TYPE
        SYNTAX  SEQUENCE OF CpqHeSysUtilPciEntry
        ACCESS  not-accessible
        STATUS  mandatory
        DESCRIPTION
            "A table of PCI utilization numbers for a whole aggregate
            PCI bus or a specific device on that bus."
        ::= { cpqHeSysUtil 6 }

    cpqHeSysUtilPciEntry OBJECT-TYPE
        SYNTAX  CpqHeSysUtilPciEntry
        ACCESS  not-accessible
        STATUS  mandatory
        DESCRIPTION
            "PCI utilization entry"
        INDEX   { cpqHeSysUtilPciIndex }
        ::= { cpqHeSysUtilPciTable 1 }

    CpqHeSysUtilPciEntry ::= SEQUENCE {
        cpqHeSysUtilPciIndex     INTEGER,
        cpqHeSysUtilPciBus       INTEGER,
        cpqHeSysUtilPciDevice    INTEGER,
        cpqHeSysUtilPciMin       INTEGER,
        cpqHeSysUtilPciFiveMin   INTEGER,
        cpqHeSysUtilPciThirtyMin INTEGER,
        cpqHeSysUtilPciHour       INTEGER,
        cpqHeSysUtilPciHwLocation DisplayString
    }

    cpqHeSysUtilPciIndex OBJECT-TYPE
        SYNTAX  INTEGER (0..255)
        ACCESS  read-only
        STATUS  mandatory
        DESCRIPTION
            "A unique index into each PCI utilization table entry. "
        ::= { cpqHeSysUtilPciEntry 1 }

    cpqHeSysUtilPciBus OBJECT-TYPE
        SYNTAX  INTEGER (0..255)
        ACCESS  read-only
        STATUS  mandatory
        DESCRIPTION
            "The PCI bus number for this set of utilization numbers. "
        ::= { cpqHeSysUtilPciEntry 2 }

    cpqHeSysUtilPciDevice OBJECT-TYPE
        SYNTAX  INTEGER
        ACCESS  read-only
        STATUS  mandatory
        DESCRIPTION
            "The PCI device number for this set of utilization numbers.
            If this value is -1, the utilization reported is for the
            aggregate of all devices on this PCI bus. "
        ::= { cpqHeSysUtilPciEntry 3 }

    cpqHeSysUtilPciMin OBJECT-TYPE
        SYNTAX  INTEGER
        ACCESS  read-only
        STATUS  mandatory
        DESCRIPTION
            "The utilization as a percentage of the theoretical
            maximum during the last minute.  A value of -1 indicates
            that the utilization number is not available."
        ::= { cpqHeSysUtilPciEntry 4 }

    cpqHeSysUtilPciFiveMin OBJECT-TYPE
        SYNTAX  INTEGER
        ACCESS  read-only
        STATUS  mandatory
        DESCRIPTION
            "The utilization as a percentage of the theoretical
            maximum during the last five minutes.  A value of -1
            indicates that the utilization number is not available."
        ::= { cpqHeSysUtilPciEntry 5 }

    cpqHeSysUtilPciThirtyMin OBJECT-TYPE
        SYNTAX  INTEGER
        ACCESS  read-only
        STATUS  mandatory
        DESCRIPTION
            "The utilization as a percentage of the theoretical
            maximum during the last thirty minutes.  A value of -1
            indicates that the utilization number is not available."
        ::= { cpqHeSysUtilPciEntry 6 }

    cpqHeSysUtilPciHour OBJECT-TYPE
        SYNTAX  INTEGER
        ACCESS  read-only
        STATUS  mandatory
        DESCRIPTION
            "The utilization as a percentage of the theoretical
            maximum during the last hour.  A value of -1 indicates
            that the utilization number is not available."
        ::= { cpqHeSysUtilPciEntry 7 }

    cpqHeSysUtilPciHwLocation OBJECT-TYPE
        SYNTAX  DisplayString (SIZE (0..255))
        ACCESS  read-only
        STATUS  optional
        DESCRIPTION
            "A text description of the hardware location, on complex
             multi SBB hardware only, for the PCI drawer.
             A NULL string indicates that the hardware location could not
             be determined or is irrelevant."
        ::= { cpqHeSysUtilPciEntry 8 }

-- ****************************************************************************
--   Health MIB Fault Tolerant Power Supply Group
--   ============================================
--
-- The compaq enterprise               (1.3.6.1.4.1.232)
--      cpqHealth Group                (1.3.6.1.4.1.232.6)
--       cpqHeComponent Group          (1.3.6.1.4.1.232.6.2)
--        cpqHeFltTolPwrSupply Group   (1.3.6.1.4.1.232.6.2.9)
--
--  The cpqHeFltTolPwrSupply group contains management information about fault
--  tolerant power supplies.
-- 
--  Implementation of the cpqHeFltTolPwrSupply group is mandatory for all
--  agents that support the Server Health MIB.
--
-- ****************************************************************************
    cpqHeFltTolPwrSupplyCondition OBJECT-TYPE
        SYNTAX  INTEGER {
            other(1),
            ok(2),
            degraded(3),
            failed(4)
            }
        ACCESS  read-only
        STATUS  mandatory
        DESCRIPTION
            "This value specifies the overall condition of the fault tolerant
             power supply sub-system."
        ::= { cpqHeFltTolPwrSupply 1 }

      cpqHeFltTolPwrSupplyStatus OBJECT-TYPE
        SYNTAX  INTEGER {
            other(1),
            notSupported(2),
            notInstalled(3),
            installed(4)
            }
        ACCESS  read-only
        STATUS  mandatory
        DESCRIPTION
            "This value specifies the status of the fault tolerant power
             supply."
        ::= { cpqHeFltTolPwrSupply 2 }

-- ****************************************************************************
--   Health MIB Fault Tolerant Power Supply Table
--   ============================================
--
-- The compaq enterprise               (1.3.6.1.4.1.232)
--      cpqHealth Group                (1.3.6.1.4.1.232.6)
--       cpqHeComponent Group          (1.3.6.1.4.1.232.6.2)
--        cpqHeFltTolPowerSupply Group (1.3.6.1.4.1.232.6.2.9)
--         cpqHeFltTolPowerSupplyTable (1.3.6.1.4.1.232.6.2.9.3)
--
-- ****************************************************************************

    cpqHeFltTolPowerSupplyTable OBJECT-TYPE
        SYNTAX  SEQUENCE OF CpqHeFltTolPowerSupplyEntry
        ACCESS  not-accessible
        STATUS  mandatory
        DESCRIPTION
            "A table of Power Supply Entries."
        ::= { cpqHeFltTolPwrSupply 3 }

    cpqHeFltTolPowerSupplyEntry OBJECT-TYPE
        SYNTAX  CpqHeFltTolPowerSupplyEntry
        ACCESS  not-accessible
        STATUS  mandatory
        DESCRIPTION
            "A Fault Tolerant Power Supply Entry."
        INDEX   { cpqHeFltTolPowerSupplyChassis, cpqHeFltTolPowerSupplyBay }
        ::= { cpqHeFltTolPowerSupplyTable 1 }

    CpqHeFltTolPowerSupplyEntry ::= SEQUENCE {
        cpqHeFltTolPowerSupplyChassis             INTEGER,
        cpqHeFltTolPowerSupplyBay                 INTEGER,
        cpqHeFltTolPowerSupplyPresent             INTEGER,
        cpqHeFltTolPowerSupplyCondition           INTEGER,
        cpqHeFltTolPowerSupplyStatus              INTEGER,
        cpqHeFltTolPowerSupplyMainVoltage         INTEGER,
        cpqHeFltTolPowerSupplyCapacityUsed        INTEGER,
        cpqHeFltTolPowerSupplyCapacityMaximum     INTEGER,
        cpqHeFltTolPowerSupplyRedundant           INTEGER,
        cpqHeFltTolPowerSupplyModel               DisplayString,
        cpqHeFltTolPowerSupplySerialNumber        DisplayString,
        cpqHeFltTolPowerSupplyAutoRev             OCTET STRING,
        cpqHeFltTolPowerSupplyHotPlug             INTEGER,
        cpqHeFltTolPowerSupplyFirmwareRev         DisplayString,
        cpqHeFltTolPowerSupplyHwLocation          DisplayString,
        cpqHeFltTolPowerSupplySparePartNum        DisplayString,
        cpqHeFltTolPowerSupplyRedundantPartner    INTEGER,
        cpqHeFltTolPowerSupplyErrorCondition      INTEGER
        }

    cpqHeFltTolPowerSupplyChassis OBJECT-TYPE
        SYNTAX  INTEGER
        ACCESS  read-only
        STATUS  mandatory
        DESCRIPTION
            "The system chassis number." 
        ::= { cpqHeFltTolPowerSupplyEntry 1 }

    cpqHeFltTolPowerSupplyBay OBJECT-TYPE
        SYNTAX  INTEGER
        ACCESS  read-only
        STATUS  mandatory
        DESCRIPTION
            "The bay number to index within this chassis."
        ::= { cpqHeFltTolPowerSupplyEntry 2 }

    cpqHeFltTolPowerSupplyPresent OBJECT-TYPE
        SYNTAX  INTEGER {
            other(1),
            absent(2),
            present(3)
            }
        ACCESS  read-only
        STATUS  mandatory
        DESCRIPTION
            "Indicates whether the power supply is present in the chassis."
        ::= { cpqHeFltTolPowerSupplyEntry 3 }

    cpqHeFltTolPowerSupplyCondition OBJECT-TYPE
        SYNTAX  INTEGER {
            other(1),
            ok(2),
            degraded(3),
            failed(4)
            }
        ACCESS  read-only
        STATUS  mandatory
        DESCRIPTION
            "The condition of the power supply.

            This value will be one of the following:

            other(1)
              The status could not be determined or not present.

            ok(2)
              The power supply is operating normally.

            degraded(3)
              A temperature sensor, fan or other power supply component is
              outside of normal operating range.

            failed(4)
              A power supply component detects a condition that could
              permanently damage the system."
        ::= { cpqHeFltTolPowerSupplyEntry 4 }

    cpqHeFltTolPowerSupplyStatus OBJECT-TYPE
        SYNTAX  INTEGER {
            noError(1),
            generalFailure(2),
            bistFailure(3),
            fanFailure(4),
            tempFailure(5),
            interlockOpen(6),
            epromFailed(7),
            vrefFailed(8),
            dacFailed(9),
            ramTestFailed(10),
            voltageChannelFailed(11),
            orringdiodeFailed(12),
            brownOut(13),
            giveupOnStartup(14),
            nvramInvalid(15),
            calibrationTableInvalid(16),
            noPowerInput(17)
            }
        ACCESS  read-only 
        STATUS  mandatory
        DESCRIPTION
            "The status of the power supply."
        ::= { cpqHeFltTolPowerSupplyEntry 5 }

    cpqHeFltTolPowerSupplyMainVoltage OBJECT-TYPE
        SYNTAX  INTEGER
        ACCESS  read-only
        STATUS  mandatory
        DESCRIPTION
            "The input main voltage of the power supply in volts."
        ::= { cpqHeFltTolPowerSupplyEntry 6 }

    cpqHeFltTolPowerSupplyCapacityUsed OBJECT-TYPE
        SYNTAX  INTEGER
        ACCESS  read-only
        STATUS  mandatory
        DESCRIPTION
            "The currently used capacity of the power supply in watts."
        ::= { cpqHeFltTolPowerSupplyEntry 7 }

    cpqHeFltTolPowerSupplyCapacityMaximum OBJECT-TYPE
        SYNTAX  INTEGER
        ACCESS  read-only
        STATUS  mandatory
        DESCRIPTION
            "The maximum capacity of the power supply in watts."
        ::= { cpqHeFltTolPowerSupplyEntry 8 }

    cpqHeFltTolPowerSupplyRedundant OBJECT-TYPE
        SYNTAX  INTEGER {
            other(1),
            notRedundant(2),
            redundant(3)
            }
        ACCESS  read-only
        STATUS  mandatory
        DESCRIPTION
            "The redundancy state of the power supply.

            This value will be one of the following:
            other(1)
              The redundancy state could not be determined.

            notRedundant(2)
              The power supply is not operating in a redundant state.

            redundant(3)
              The power supply is operating in a redundant state."
        ::= { cpqHeFltTolPowerSupplyEntry 9 }

    cpqHeFltTolPowerSupplyModel OBJECT-TYPE
        SYNTAX  DisplayString (SIZE (0..80))
        ACCESS  read-only
        STATUS  mandatory
        DESCRIPTION
            "The power supply model name."
        ::= { cpqHeFltTolPowerSupplyEntry 10 }

    cpqHeFltTolPowerSupplySerialNumber OBJECT-TYPE
        SYNTAX  DisplayString (SIZE (0..80))
        ACCESS  read-only
        STATUS  mandatory
        DESCRIPTION
            "The power supply serial number."
        ::= { cpqHeFltTolPowerSupplyEntry 11 }

    cpqHeFltTolPowerSupplyAutoRev OBJECT-TYPE
        SYNTAX  OCTET STRING (SIZE (0..4))
        ACCESS  read-only
        STATUS  mandatory
        DESCRIPTION
            "The power supply auto revision number."
        ::= { cpqHeFltTolPowerSupplyEntry 12 }

    cpqHeFltTolPowerSupplyHotPlug OBJECT-TYPE
        SYNTAX  INTEGER {
            other(1),
            nonHotPluggable(2),
            hotPluggable(3)
            }
        ACCESS  read-only
        STATUS  mandatory
        DESCRIPTION
            "This indicates if the power supply is capable of being
            removed and/or inserted while the system is in an operational
            state.

            If the value is hotPluggable(3), the power supply can be safely
            removed if and only if the cpqHeFltTolPowerSupplyRedundant
            field is in a redundant(3) state.

            This value will be one of the following:
            other(1)
              The state could not be determined.

            nonHotPluggable(2)
              The power supply is not hot plug capable.

            hotPluggable(3)
              The power supply is hot plug capable and can be removed if
              the system is operating in a redundant state.  A power
              supply may be added to an empty power supply bay."
        ::= { cpqHeFltTolPowerSupplyEntry 13 }

    cpqHeFltTolPowerSupplyFirmwareRev OBJECT-TYPE
        SYNTAX  DisplayString (SIZE (0..24))
        ACCESS  read-only
        STATUS  mandatory
        DESCRIPTION
            "The power supply firmware revision.  This field will be left
            blank if the firmware revision is unknown."
        ::= { cpqHeFltTolPowerSupplyEntry 14 }

    cpqHeFltTolPowerSupplyHwLocation OBJECT-TYPE
        SYNTAX  DisplayString (SIZE (0..255))
        ACCESS  read-only
        STATUS  optional
        DESCRIPTION
            "A text description of the hardware location, on complex
             multi SBB hardware only, for the power supply.
             A NULL string indicates that the hardware location could not
             be determined or is irrelevant."
        ::= { cpqHeFltTolPowerSupplyEntry 15 }

    cpqHeFltTolPowerSupplySparePartNum OBJECT-TYPE
        SYNTAX  DisplayString (SIZE (0..80))
        ACCESS  read-only
        STATUS  optional
        DESCRIPTION
            "The power supply part number or spare part number."
        ::= { cpqHeFltTolPowerSupplyEntry 16 }

    cpqHeFltTolPowerSupplyRedundantPartner OBJECT-TYPE
        SYNTAX  INTEGER
        ACCESS  read-only
        STATUS  mandatory
        DESCRIPTION
            "This specifies the index of the redundant partner. A value
            of zero will be used if there is no redundant partner."
        ::= { cpqHeFltTolPowerSupplyEntry 17 }

    cpqHeFltTolPowerSupplyErrorCondition OBJECT-TYPE
        SYNTAX  INTEGER {
            noError(1),
            generalFailure(2),
            overvoltage(3),
            overcurrent(4),
            overtemperature(5),
            powerinputloss(6),
            fanfailure(7),
            vinhighwarning(8),
            vinlowwarning(9),
            vouthighwarning(10),
            voutlowwarning(11),
            inlettemphighwarning(12),
            iinternaltemphighwarning(13),
            vauxhighwarning(14),
            vauxlowwarning(15)
            }
        ACCESS  read-only 
        STATUS  mandatory
        DESCRIPTION
            "The Error condition of the power supply."
        ::= { cpqHeFltTolPowerSupplyEntry 18 }

-- ****************************************************************************
--   Health MIB Integrated Remote Console (IRC) Group
--   ================================================
-- 
-- The compaq enterprise               (1.3.6.1.4.1.232)
--      cpqHealth Group                (1.3.6.1.4.1.232.6)
--       cpqHeComponent Group          (1.3.6.1.4.1.232.6.2)
--        cpqHeIRC Group               (1.3.6.1.4.1.232.6.2.10)
--
--  The cpqHeIRC group contains management information about the Integrated
--  Remote Console ASIC.
--
--  Implementation of the cpqHeIRC group is mandatory for all agents that
--  support the Server Health MIB.
--
-- ****************************************************************************

    cpqHeIRCStatus OBJECT-TYPE
        SYNTAX INTEGER {
            unknown(1),
            notavailable(2),
            disabled(3),
            enabled(4)
            }
        ACCESS read-only
        STATUS mandatory
        DESCRIPTION
            "The status of the Integrated Remote Console.  A value of notavailable
             will be returned if this system does not contain IRC."

        ::= { cpqHeIRC 1 }

-- ****************************************************************************
--   Health MIB System Event Log Group
--   =================================
--
-- The compaq enterprise               (1.3.6.1.4.1.232)
--      cpqHealth Group                (1.3.6.1.4.1.232.6)
--       cpqHeComponent Group          (1.3.6.1.4.1.232.6.2)
--        cpqHeEventLog Group          (1.3.6.1.4.1.232.6.2.11)
--
--  The cpqHeEventLog group describes the health system event log.
--
--  Implementation of the cpqHeEventLog group is mandatory for all
--  agents that support the Server Health MIB.
--
-- ****************************************************************************

    cpqHeEventLogSupported OBJECT-TYPE
        SYNTAX  INTEGER {
            other(1),
            notSupported(2),
            supported(3),
            clear(4)             -- Settable value to clear the log
            }
        ACCESS  read-write
        STATUS  mandatory
        DESCRIPTION
            "This value specifies if this system supports the Integrated
            Management Log feature.

            An SNMP set of the value clear(4) will clear the System Event
            Log of all entries."
        ::= { cpqHeEventLog 1 }

    cpqHeEventLogCondition OBJECT-TYPE
        SYNTAX  INTEGER {
            other(1),
            ok(2),
            degraded(3),
            failed(4)
            }
        ACCESS  read-only
        STATUS  mandatory
        DESCRIPTION
            "This value specifies the overall condition of the Integrated
            Management Log feature."
        ::= { cpqHeEventLog 2 }

-- ****************************************************************************
--   Health MIB System Event Log Table
--   =================================
--
-- The compaq enterprise               (1.3.6.1.4.1.232)
--      cpqHealth Group                (1.3.6.1.4.1.232.6)
--       cpqHeComponent Group          (1.3.6.1.4.1.232.6.2)
--        cpqHeEventLog Group          (1.3.6.1.4.1.232.6.2.11)
--         cpqHeEventLogTable          (1.3.6.1.4.1.232.6.2.11.3)
--
-- ****************************************************************************

    cpqHeEventLogTable OBJECT-TYPE
        SYNTAX  SEQUENCE OF CpqHeEventLogEntry
        ACCESS  not-accessible
        STATUS  mandatory
        DESCRIPTION
            "A table of System Event Log Entries."
        ::= { cpqHeEventLog 3 }

    cpqHeEventLogEntry OBJECT-TYPE
        SYNTAX  CpqHeEventLogEntry
        ACCESS  not-accessible
        STATUS  mandatory
        DESCRIPTION
            "A System Event Log Entry."
        INDEX   { cpqHeEventLogEntryNumber }
        ::= { cpqHeEventLogTable 1 }

    CpqHeEventLogEntry ::= SEQUENCE {
        cpqHeEventLogEntryNumber         INTEGER,
        cpqHeEventLogEntrySeverity       INTEGER,
        cpqHeEventLogEntryClass          INTEGER,
        cpqHeEventLogEntryCode           INTEGER,
        cpqHeEventLogEntryCount          INTEGER,
        cpqHeEventLogInitialTime         OCTET STRING,
        cpqHeEventLogUpdateTime          OCTET STRING,
        cpqHeEventLogErrorDesc           DisplayString,
        cpqHeEventLogFreeFormData        OCTET STRING
    }

    cpqHeEventLogEntryNumber OBJECT-TYPE
        SYNTAX  INTEGER
        ACCESS  read-only
        STATUS  mandatory
        DESCRIPTION
            "A number that uniquely specifies this system event log
            entry."
        ::= { cpqHeEventLogEntry 1 }

    cpqHeEventLogEntrySeverity OBJECT-TYPE
        SYNTAX  INTEGER {
            informational(2),   -- informational with no action required
            infoWithAlert(3),   -- informational but with LCD alert message
            repaired(6),        -- corrective action taken
            caution(9),         -- non-fatal error condition
            critical(15)        -- component failure
            }
        ACCESS  read-write
        STATUS  mandatory
        DESCRIPTION
            "This value specifies the severity of the event log entry.
            A caution or critical entry can have it's severity 
            lowered by setting this variable to the repaired state."
        ::= { cpqHeEventLogEntry 2 }

    cpqHeEventLogEntryClass OBJECT-TYPE
        SYNTAX  INTEGER
        ACCESS  read-only
        STATUS  mandatory
        DESCRIPTION
            "This value specifies the event log entry class designation."
        ::= { cpqHeEventLogEntry 3 }

    cpqHeEventLogEntryCode OBJECT-TYPE
        SYNTAX  INTEGER
        ACCESS  read-only
        STATUS  mandatory
        DESCRIPTION
            "This value specifies the event log entry code designation.
            The meaning of this changes depending on the class."
        ::= { cpqHeEventLogEntry 4 }

    cpqHeEventLogEntryCount OBJECT-TYPE
        SYNTAX  INTEGER
        ACCESS  read-only
        STATUS  mandatory
        DESCRIPTION
            "This value specifies the event log entry occurrence count.
            This represents the number of times this event has occurred
            starting from the initial time until the last modified time."
        ::= { cpqHeEventLogEntry 5 }

    cpqHeEventLogInitialTime OBJECT-TYPE
        SYNTAX  OCTET STRING (SIZE (6))
        ACCESS  read-only
        STATUS  mandatory
        DESCRIPTION
            "The time stamp when the event log entry was first created.

             field  octets  contents                  range
             =====  ======  ========                  =====
               1      1-2   year                      0..65536
               2       3    month                     1..12
               3       4    day                       1..31
               4       5    hour                      0..23
               5       6    minute                    0..59

            The year field is set with the most significant octet first.
            A value of 0 in the year indicates an unknown time stamp."
        ::= { cpqHeEventLogEntry 6 }

    cpqHeEventLogUpdateTime OBJECT-TYPE
        SYNTAX  OCTET STRING (SIZE (6))
        ACCESS  read-only
        STATUS  mandatory
        DESCRIPTION
            "The time stamp when the event log entry was last modified.

             field  octets  contents                  range
             =====  ======  ========                  =====
               1      1-2   year                      0..65536
               2       3    month                     1..12
               3       4    day                       1..31
               4       5    hour                      0..23
               5       6    minute                    0..59

            The year field is set with the most significant octet first.
            A value of 0 in the year indicates an unknown time stamp."
        ::= { cpqHeEventLogEntry 7 }

    cpqHeEventLogErrorDesc OBJECT-TYPE
        SYNTAX  DisplayString (SIZE (0..255))
        ACCESS  read-only
        STATUS  mandatory
        DESCRIPTION
            "A text description of the event log entry."
        ::= { cpqHeEventLogEntry 8 }

    cpqHeEventLogFreeFormData OBJECT-TYPE
        SYNTAX  OCTET STRING (SIZE (0..128))
        ACCESS  read-only
        STATUS  mandatory
        DESCRIPTION
            "This is the free form data associated with a particular
            event."
        ::= { cpqHeEventLogEntry 9 }

-- ****************************************************************************
--   Health MIB Management Display Group
--   ===================================
--
-- The compaq enterprise               (1.3.6.1.4.1.232)
--      cpqHealth Group                (1.3.6.1.4.1.232.6)
--       cpqHeComponent Group          (1.3.6.1.4.1.232.6.2)
--        cpqHeMgmtDisplay Group       (1.3.6.1.4.1.232.6.2.12)
--
-- **************************************************************************** 

--  The cpqHeMgmtDisplay group maintains information about the Management
--  Display device.
--
--  Implementation of the cpqHeTrap group is mandatory for agents that
--  support the Server Health MIB.

    cpqHeMgmtDisplayType OBJECT-TYPE
        SYNTAX  INTEGER {
            other(1),            -- Unknown device or could not be determined
            none(2),             -- No Management display device
            imd4x16(3),          -- IMD display (4 lines by 16 chars)
            ocp1x16(4)           -- Digital OCP display (1 line by 16 chars)
            }
        ACCESS  read-only
        STATUS  mandatory
        DESCRIPTION
            "This value specifies the type of Management Display device.
            If a display device is available on the server, the type
            will be set accordingly.  If no device is present, the value
            will be set to none(2)."
        ::= { cpqHeMgmtDisplay 1 }

    cpqHeMgmtDisplayText OBJECT-TYPE
        SYNTAX  DisplayString (SIZE (0..255))
        ACCESS  read-write
        STATUS  mandatory
        DESCRIPTION
            "The text to be written to the Management display device.

            If this item is read, it may not accurately reflect what
            is currently displayed."
        ::= { cpqHeMgmtDisplay 2 }

    cpqHeMgmtUID OBJECT-TYPE
        SYNTAX  INTEGER {
            other(1),            -- Unknown device or could not be determined
            none(2),             -- No unit identifier device
            ledOn(3),            -- Unit identifier LED is On
            ledOff(4),           -- Unit identifier LED is Off
            ledBlinking(5)       -- Unit identifier LED is Blinking
            }
        ACCESS  read-write
        STATUS  mandatory
        DESCRIPTION
            "The Unit Identifier LED.

            This value will be one of the following:

            other(1)
              The state of the LED could not be determined.  Setting the
              LED state is not allowed.

            none(2)
              The LED is not present.  Setting LED state is not allowed.

            ledOn(3)
              The LED is present and ON.  The LED can be turned Off or Blinking
              by setting the cpqHeMgmtUID to ledOff(4) or ledBlinking(5) respectively.

            ledOff(4)
              The LED is present and OFF.  The LED can be turned On or Blinking
              by setting the cpqHeMgmtUID to ledOn(3) or ledBlinking(5) respectively.

            ledBlinking(5)
              The LED is present and is Blinking.  The LED can be turned On or Off
              by setting the cpqHeMgmtUID to ledOn(3) or ledOff(4) respectively"
        ::= { cpqHeMgmtDisplay 3 }

-- ****************************************************************************
--   Health MIB Power Converter Group
--   ================================
--
-- The compaq enterprise               (1.3.6.1.4.1.232)
--      cpqHealth Group                (1.3.6.1.4.1.232.6)
--       cpqHeComponent Group          (1.3.6.1.4.1.232.6.2)
--        cpqHePowerConverter Group    (1.3.6.1.4.1.232.6.2.13)
--
--  The cpqHePowerConverter group describes the power converter modules
--  in the system.
--
--  Implementation of the cpqHePowerConverter group is mandatory for all
--  agents that support the Server Health MIB.
--
-- ****************************************************************************

    cpqHePowerConverterSupported OBJECT-TYPE
        SYNTAX  INTEGER {
            other(1),
            notSupported(2),
            supported(3)
            }
        ACCESS  read-only
        STATUS  mandatory
        DESCRIPTION
            "This value specifies if this system supports reporting
            power converter module information."
        ::= { cpqHePowerConverter 1 }

    cpqHePowerConverterCondition OBJECT-TYPE
        SYNTAX  INTEGER {
            other(1),
            ok(2),
            degraded(3),
            failed(4)
            }
        ACCESS  read-only
        STATUS  mandatory
        DESCRIPTION
            "This value specifies the overall condition of the power
            converters modules in the system."
        ::= { cpqHePowerConverter 2 }

-- ****************************************************************************
--   Health MIB Power Converter Table
--   ================================
--
-- The compaq enterprise               (1.3.6.1.4.1.232)
--      cpqHealth Group                (1.3.6.1.4.1.232.6)
--       cpqHeComponent Group          (1.3.6.1.4.1.232.6.2)
--        cpqHePowerConverter Group    (1.3.6.1.4.1.232.6.2.13)
--         cpqHePowerConverterTable    (1.3.6.1.4.1.232.6.2.13.3)
--
-- ****************************************************************************

    cpqHePowerConverterTable OBJECT-TYPE
        SYNTAX  SEQUENCE OF CpqHePowerConverterEntry
        ACCESS  not-accessible
        STATUS  mandatory
        DESCRIPTION
            "A table of Power Converter Module Entries."
        ::= { cpqHePowerConverter 3 }

    cpqHePowerConverterEntry OBJECT-TYPE
        SYNTAX  CpqHePowerConverterEntry
        ACCESS  not-accessible
        STATUS  mandatory
        DESCRIPTION
            "A Power Converter Module Entry."
        INDEX   { cpqHePwrConvChassis, cpqHePwrConvIndex }
        ::= { cpqHePowerConverterTable 1 }

    CpqHePowerConverterEntry ::= SEQUENCE {
        cpqHePwrConvChassis             INTEGER,
        cpqHePwrConvIndex               INTEGER,
        cpqHePwrConvPresent             INTEGER,
        cpqHePwrConvSlot                INTEGER,
        cpqHePwrConvSocket              INTEGER,
        cpqHePwrConvRedundant           INTEGER,
        cpqHePwrConvRedundantGroupId    INTEGER,
        cpqHePwrConvCondition           INTEGER,
        cpqHePwrConvHwLocation          DisplayString
    }

    cpqHePwrConvChassis OBJECT-TYPE
        SYNTAX  INTEGER
        ACCESS  read-only
        STATUS  mandatory
        DESCRIPTION
            "The system chassis number containing the power converter
            modules."
        ::= { cpqHePowerConverterEntry 1 }

    cpqHePwrConvIndex OBJECT-TYPE
        SYNTAX  INTEGER
        ACCESS  read-only
        STATUS  mandatory
        DESCRIPTION
            "The Power Converter Module number to index within the chassis."
        ::= { cpqHePowerConverterEntry 2 }

    cpqHePwrConvPresent OBJECT-TYPE
        SYNTAX  INTEGER {
            other(1),
            absent(2),
            present(3)
            } 
        ACCESS  read-only
        STATUS  mandatory
        DESCRIPTION
            "This specifies if the Power Converter Module described is
            present in the system."
        ::= { cpqHePowerConverterEntry 3 }

    cpqHePwrConvSlot OBJECT-TYPE
        SYNTAX  INTEGER
        ACCESS  read-only
        STATUS  mandatory
        DESCRIPTION
            "The Power Converter Module slot number within the chassis."
        ::= { cpqHePowerConverterEntry 4 }

    cpqHePwrConvSocket OBJECT-TYPE
        SYNTAX  INTEGER
        ACCESS  read-only
        STATUS  mandatory
        DESCRIPTION
            "The Power Converter Module socket number within the slot."
        ::= { cpqHePowerConverterEntry 5 }

    cpqHePwrConvRedundant OBJECT-TYPE
        SYNTAX  INTEGER {
            other(1),
            nonRedundant(2),
            redundant(3)
            }
        ACCESS  read-only
        STATUS  mandatory
        DESCRIPTION
            "This specifies if the Power Converter Module is redundant."
        ::= { cpqHePowerConverterEntry 6 }

    cpqHePwrConvRedundantGroupId OBJECT-TYPE
        SYNTAX  INTEGER
        ACCESS  read-only
        STATUS  mandatory
        DESCRIPTION
            "The Power Converter Module group id.  A redundant set of
            power converters will have the same group id."
        ::= { cpqHePowerConverterEntry 7 }

    cpqHePwrConvCondition OBJECT-TYPE
        SYNTAX  INTEGER {
            other(1),
            ok(2),
            degraded(3),
            failed(4)
            }
        ACCESS  read-only
        STATUS  mandatory
        DESCRIPTION
            "The Power Converter Module condition."
        ::= { cpqHePowerConverterEntry 8 }

    cpqHePwrConvHwLocation OBJECT-TYPE
        SYNTAX  DisplayString (SIZE (0..255))
        ACCESS  read-only
        STATUS  optional
        DESCRIPTION
            "A text description of the hardware location, on complex
             multi SBB hardware only, for the power converter.
             A NULL string indicates that the hardware location could not
             be determined or is irrelevant."
        ::= { cpqHePowerConverterEntry 9 }

-- ****************************************************************************
--   Health MIB Advanced Memory Protection Group (formerly Resilient Memory)
--   =======================================================================
--
-- The compaq enterprise               (1.3.6.1.4.1.232)
--      cpqHealth Group                (1.3.6.1.4.1.232.6)
--       cpqHeComponent Group          (1.3.6.1.4.1.232.6.2)
--        cpqHeResilientMemory Group   (1.3.6.1.4.1.232.6.2.14)
--
--  The cpqHeResilientMemory group describes the Advanced Memory Protection
--  sub-system in the server.
--
--  Implementation of the cpqHeResilientMemory group is mandatory for all
--  Server Agents that support the Server Health MIB.
--
-- ****************************************************************************

    cpqHeResilientMemTypeActive OBJECT-TYPE
        SYNTAX  INTEGER {
            other(1),
            none(2),
            onLineSpare(3),           
            mirrored(4),               -- deprecated
            advancedEcc(5),
            mirroredSingleBoard(6),
            mirroredDualBoard(7),
            xor(8),
            lockStep(9),
	    onLineSpareChannel(10),
	    onLineSpareRank(11),
	    mirroringIntrasocket(12),
	    mirroringIntersocket(13)
            }
        ACCESS  read-only
        STATUS  mandatory
        DESCRIPTION
            "This value specifies the type of Advanced Memory Protection fault
            tolerance currently active on the system.

            The following connection states are supported:

            other(1)
              The Advanced Memory Protection fault tolerance cannot be
              determined by the Management Agent.  You may need to upgrade
              your software.

            none(2)
              This system is not configured for Advanced Memory Protection
              fault tolerance or Advanced Memory Protection is not available
              on this system.

            onLineSpare(3)
              This system is configured for Online Spare Advanced Memory
              Protection.

            mirrored(4)
              This system is configured for Mirrored Advanced Memory
              Protection.

            advancedECC(5)
              This system is configured for the Advanced ECC type of
              Advanced Memory Protection.

            mirroredSingleBoard(6)
              This system is configured for Mirrored Advanced Memory
              Protection within a single memory board.

            mirroredDualBoard(7)
              This system is configured for Mirrored Advanced Memory
              Protection within a dual memory board configuration. The
              mirrored memory may be swapped with memory on the same
              memory board or with memory on the second memory board.

            xor(8)
              This system is configured for Advanced Memory Protection
              using the XOR engine.
              
            lockStep(9)
              This system is configured for LockStep type of 
              Advanced Memory Protection.

            onLineSpareChannel(10)
              This system is configured for Online Spare Channel Advanced 
	      Memory Protection.

            onLineSpareRank(11)
              This system is configured for Online Spare Rank Advanced 
	      Memory Protection.

            mirroringIntrasocket(12)
              This system is configured for Mirrored Intrasocket Advanced 
	      Memory Protection between memory of single processor or board.

            mirroringIntersocket(13)
              This system is configured for Mirrored Intersocket Advanced 
	      Memory Protection between memory of two processors or boards."
        ::= { cpqHeResilientMemory 1 }

    cpqHeResilientMemTypeAvailable OBJECT-TYPE
        SYNTAX  INTEGER
        ACCESS  read-only
        STATUS  mandatory
        DESCRIPTION
            "This value specifies the type of Advanced Memory Protection
            Fault Tolerance available on the system.

            This is a collection of flags used to indicate the fault
            Advanced Memory Protection options available. This integer
            is a bitmap, with each bit indicating the availability of an
            option. If the bit is set to 1, the option is available;
            otherwise it is not. Multiple options are allowed.

            NOTE:   bit 31 is the most significant bit, bit 0 is the least
                    significant.

                    Bit 31-11:  RESERVED (0)
                    Bit 10:     Mirroring Intersocket
                    Bit 9:      Mirroring Intrasocket
                    Bit 8:     Online Rank Spare
                    Bit 7:     Online Channel Spare
                    Bit 6:     LockStep
                    Bit 5:     XOR
                    Bit 4:     Mirrored Memory with dual memory boards 
                    Bit 3:     Mirrored Memory within a single memory board 
                    Bit 2:     Advanced ECC
                    Bit 1:     Mirrored (deprecated)
                    Bit 0:     Online Spare" 
        ::= { cpqHeResilientMemory 2 }

    cpqHeResilientMemStatus OBJECT-TYPE
        SYNTAX  INTEGER {
            other(1),
            notProtected(2),
            protected(3),
            degraded(4),
            dimmEcc(5),
            mirrorNoFaults(6),
            mirrorWithFaults(7),
            hotSpareNoFaults(8),
            hotSpareWithFaults(9),
            xorNoFaults(10),
            xorWithFaults(11),
            advancedEcc(12),
            advancedEccWithFaults(13),            
            lockStep(14),
            lockStepWithFaults(15)            
            }
        ACCESS  read-only
        STATUS  mandatory
        DESCRIPTION
            "This value specifies the current state of the Advanced
            Memory Protection subsystem.

            The following states are supported:

            other(1)
              The system does not support Advanced Memory Protection or the
              status cannot be determined by the Management Agent.

            notProtected(2)
              This system supports Advanced Memory Protection but the
              feature is disabled.

            protected(3)
              The system is protected by Advanced Memory Protection.

            degraded(4)
              The system was protected, but the Advanced Memory
              Protection feature has been engaged.

            dimmEcc(5)
              The system is protected via DIMM ECC only.

            mirrorNoFaults(6)
              The system is protected by Advanced Memory Protection in the
              mirrored mode.  No DIMM faults have been detected.

            mirrorWithFaults(7)
              The system is protected by Advanced Memory Protection in the
              mirrored mode.  One or more DIMM faults have been detected.

            hotSpareNoFaults(8)
              The system is protected by Advanced Memory Protection in the
              hot spare mode.  No DIMM faults have been detected.

            hotSpareWithFaults(9)
              The system is protected by Advanced Memory Protection in the
              hot spare mode.  One or more DIMM faults have been detected.

            xorNoFaults(10)
              The system is protected by Advanced Memory Protection in the
              XOR memory mode.  No DIMM faults have been detected.

            xorWithFaults(11)
              The system is protected by Advanced Memory Protection in the
              XOR memory mode.  One or more DIMM faults have been detected.

            advancedEcc(12)
              The system is protected by Advanced Memory Protection in the
              Advanced ECC mode.
              
            advancedEccWithFaults(13)
              The system is protected by Advanced Memory Protection in the
              Advanced ECC mode. One or more DIMM faults have been detected.

            lockStep(14)
              The system is protected by Advanced Memory Protection in the
              Lock Step mode.
              
            localStepWithFaults(15)
              The system is protected by Advanced Memory Protection in the
              Lock Step mode. One or more DIMM faults have been detected."              
        ::= { cpqHeResilientMemory 3 }

    cpqHeResilientMemCondition OBJECT-TYPE
        SYNTAX  INTEGER {
            other(1),
            ok(2),
            degraded(3)
            }
        ACCESS  read-only
        STATUS  mandatory
        DESCRIPTION
            "This value specifies the current condition of the Advanced
            Memory Protection subsystem.

            The following states are supported:

            other(1)
              The system does not support fault tolerant memory or the
              state cannot be determined by the Management Agent.

            ok(2)
              This system is operating normally.

            degraded(3)
              The system is running in a degraded state because the
              Advanced Memory Protection subsystem has been engaged."
        ::= { cpqHeResilientMemory 4 }

    cpqHeResilientMemHotPlug OBJECT-TYPE
        SYNTAX  INTEGER {
            other(1),
            nonHotPluggable(2),
            hotPluggable(3)
            }
        ACCESS  read-only
        STATUS  mandatory
        DESCRIPTION
            "This value specifies the current condition of the Advanced
            Memory Protection subsystem.

            The following states are supported:

            other(1)
              The state could not be determined or the system does not
              support Advanced Memory Protection.

            nonHotPluggable(2)
              The memory board or cartridge is not hot plug capable.

            hotPluggable(3)
              The memory board or cartridge is hot plug capable and can be
              removed if the system is operating in a redundant state.  A
              memory board or cartridge may be added to an empty bay."
        ::= { cpqHeResilientMemory 5 }

    cpqHeResilientMemOperatingSpeed OBJECT-TYPE
        SYNTAX  INTEGER
        ACCESS  read-only
        STATUS  mandatory
        DESCRIPTION
            "This value specifies the current operating speed of the Advanced
            Memory Protection subsystem in MHz.

            If this system does not support Advanced Memory Protection or this
            value cannot be determined, then a value of 0 will be returned."
        ::= { cpqHeResilientMemory 6 }

    cpqHeResilientMemOsMemSize OBJECT-TYPE
        SYNTAX  INTEGER
        ACCESS  read-only 
        STATUS  mandatory
        DESCRIPTION
            "This value specifies the size of memory as seen by the Operating
            System in MB (1 MB = 1048576 bytes).

            If this system does not support Advanced Memory Protection or this
            value cannot be determined, then a value of 0 will be returned."
        ::= { cpqHeResilientMemory 7 }

    cpqHeResilientMemTotalMemSize OBJECT-TYPE
        SYNTAX  INTEGER
        ACCESS  read-only
        STATUS  mandatory
        DESCRIPTION
            "This value specifies the total size of memory including memory seen
            by the Operating System and the memory used for spare, mirrored, or
            RAID configurations in MB (1 MB = 1048576 bytes).

            If this system does not support Advanced Memory Protection or this
            value cannot be determined, then a value of 0 will be returned."
        ::= { cpqHeResilientMemory 8 }

    cpqHeResilientMemRivState OBJECT-TYPE
        SYNTAX  INTEGER { 
            other(1),
            inactive(2),
            rebuilding(3),
            initializing(4),
            verifying(5)
            }
        ACCESS  read-only
        STATUS  mandatory
        DESCRIPTION
            "This value specifies the state of the Rebuild/Initialize/Verify
            (RIV) engine of the Advanced Memory Protection sub-system.

            The following states are supported:

            other(1)
              The system does not support Advanced Memory Protection or this
              value cannot be determined,

            inactive(2)
              The RIV engine is idle.

            rebuilding(3)
              The RIV engine is rebuilding the XOR data.

            initializing(4)
              The RIV engine is initializing memory.

            verifying(5)
              The RIV engine is verifying memory integrity."
        ::= { cpqHeResilientMemory 9 }

-- ****************************************************************************
--   Health MIB Advanced Memory Protection Board Group
--   =================================================
--
-- The compaq enterprise               (1.3.6.1.4.1.232)
--      cpqHealth Group                (1.3.6.1.4.1.232.6)
--       cpqHeComponent Group          (1.3.6.1.4.1.232.6.2)
--        cpqHeResilientMemory Group   (1.3.6.1.4.1.232.6.2.14)
--         cpqHeResMemBoardTable       (1.3.6.1.4.1.232.6.2.14.10)
--          cpqHeResMemBoardEntry      (1.3.6.1.4.1.232.6.2.14.10.1)
--
-- ****************************************************************************

    cpqHeResMemBoardTable OBJECT-TYPE
        SYNTAX  SEQUENCE OF CpqHeResMemBoardEntry
        ACCESS  not-accessible
        STATUS  mandatory
        DESCRIPTION
            "A table of memory board or cartridge descriptions in Advanced
            Memory Protection systems."
        ::= { cpqHeResilientMemory 10 }

    cpqHeResMemBoardEntry OBJECT-TYPE
        SYNTAX  CpqHeResMemBoardEntry
        ACCESS  not-accessible
        STATUS  mandatory
        DESCRIPTION
            "A memory board or cartridge description."
        INDEX   { cpqHeResMemBoardSlotIndex }
        ::= { cpqHeResMemBoardTable 1 }

    CpqHeResMemBoardEntry ::= SEQUENCE {
        cpqHeResMemBoardSlotIndex       INTEGER,
        cpqHeResMemBoardOnlineStatus    INTEGER,
        cpqHeResMemBoardErrorStatus     INTEGER,
        cpqHeResMemBoardLocked          INTEGER,
        cpqHeResMemBoardNumSockets      INTEGER,
        cpqHeResMemBoardOsMemSize       INTEGER,
        cpqHeResMemBoardTotalMemSize    INTEGER,
        cpqHeResMemBoardCondition       INTEGER,
        cpqHeResMemBoardHotPlug         INTEGER
    }

    cpqHeResMemBoardSlotIndex OBJECT-TYPE
        SYNTAX  INTEGER
        ACCESS  read-only
        STATUS  mandatory
        DESCRIPTION
            "The slot in which the memory board or cartridge is installed."
        ::= { cpqHeResMemBoardEntry 1 }

    cpqHeResMemBoardOnlineStatus OBJECT-TYPE
        SYNTAX  INTEGER {
            other(1),
            present(2),
            absent(3)
        }
        ACCESS  read-only
        STATUS  mandatory
        DESCRIPTION
            "The online status of the Advanced Memory Protection board or
            cartridge.

            The following status values are supported:

                 other(1)
                   The value is unsupported or could not be determined.

                 present(2)
                   The board or cartridge has memory and is currently online.

                 absent(3)
                   The board or cartridge is missing or offline."
        ::= { cpqHeResMemBoardEntry 2 }

    cpqHeResMemBoardErrorStatus OBJECT-TYPE
        SYNTAX  INTEGER {
            other(1),
            noError(2),
            dimmEccError(3),
            unlockError(4),
            configError(5),
            busError(6),
            powerError(7),
            advancedEcc(8),
            onlineSpare(9),
            mirrored(10),
            mirroredDimmError(11),
            memoryRaid(12),
            raidDimmError(13),
            lockstep(14),
            lockstepDimmError(15)
        }
        ACCESS  read-only
        STATUS  mandatory
        DESCRIPTION

            "The error status of the Advanced Memory Protection board or
            cartridge.

            The following status values are supported:

                 other(1)
                   The value is unsupported or could not be determined.

                 noError(2)
                   The board or cartridge is configured and operating correctly.

                 dimmEccError(3)
                   The board or cartridge has at least one DIMM ECC error.

                 unlockError(4)
                   The board or cartridge is unlocked when it should not be.
                   Please insure the board of cartridge is locked.

                 configError(5)
                   The board or cartridge has a bad memory configuration.
                   Please insure all memory modules are of the correct type,
                   speed, latency, etc.

                 busError(6)
                   The board or cartridge has a memory bus error.
                   Please insure all memory modules are of the correct type,
                   speed, latency, etc.  Also insure the cartridge is inserted
                   properly.

                 powerError(7)
                   The board or cartridge has power error.
                   Please insure all memory modules are of the correct type,
                   speed, latency, etc.  Also insure the cartridge is inserted
                   properly.

                 advancedEcc(8),
                   The board or cartridge is configured for advanced Ecc mode.

                 onlineSpare(9),
                   The board or cartridge is configured for Online Spare mode.

                 mirrored(10),
                   The board or cartridge is configured for mirrored mode.

                 mirroredDimmError(11),
                   The board or cartridge has a mirrored Dimm error.

                 memoryRaid(12),
                   The board or cartridge is configured for memory raid mode.

                 raidDimmError(13)
                   The board or cartridge has a raid Dimm error.
                   
                 lockstep(14)
                   The board or cartridge is configured for LockStep.
                   
                 lockstepDimmError(15)
                   The board or cartridge has a lockStep Dimm error."
        ::= { cpqHeResMemBoardEntry 3 }

    cpqHeResMemBoardLocked OBJECT-TYPE
        SYNTAX  INTEGER {
            other(1),
            unlocked(2),
            locked(3)
        }
        ACCESS  read-only
        STATUS  mandatory
        DESCRIPTION
            "The locked state of the Advanced Memory Protection board or
            cartridge.

            The following status values are supported:

                 other(1)
                   The value is unsupported or could not be determined.  If the
                   system does not support hot plugging of the board or
                   cartridge, then this value will be returned.

                 unlocked(2)
                   The board or cartridge is currently unlocked and may be
                   removed.

                 locked(3)
                   The board or cartridge is currently locked and may not be
                   removed."
        ::= { cpqHeResMemBoardEntry 4 }

    cpqHeResMemBoardNumSockets OBJECT-TYPE
        SYNTAX  INTEGER
        ACCESS  read-only
        STATUS  mandatory
        DESCRIPTION
            "The total number of memory sockets for this memory board or
            cartridge.

            If this value could not be determined, or if the board or
            cartridge has been removed, this value will be -1."
        ::= { cpqHeResMemBoardEntry 5 }

    cpqHeResMemBoardOsMemSize OBJECT-TYPE
        SYNTAX  INTEGER
        ACCESS  read-only
        STATUS  mandatory
        DESCRIPTION
            "This value specifies the size of memory for this board or
            cartridge as seen by the Operating System in MB (1 MB =
            1048576 bytes).

            If this system does not support Advanced Memory Protection or this
            value cannot be determined, then a value of 0 will be returned."
        ::= { cpqHeResMemBoardEntry 6 }

    cpqHeResMemBoardTotalMemSize OBJECT-TYPE
        SYNTAX  INTEGER
        ACCESS  read-only
        STATUS  mandatory
        DESCRIPTION
            "This value specifies the size of memory for this board or
            cartridge including memory seen by the Operating System and
            the memory used for spare, mirrored, or XOR configurations
            in MB (1 MB = 1048576 bytes).

            If this system does not support Advanced Memory Protection or this
            value cannot be determined, then a value of 0 will be returned."
        ::= { cpqHeResMemBoardEntry 7 }

    cpqHeResMemBoardCondition OBJECT-TYPE
        SYNTAX  INTEGER {
            other(1),
            ok(2),
            degraded(3)
        }
        ACCESS  read-only
        STATUS  mandatory
        DESCRIPTION
             "This provides the current status of the Advanced Memory
              Protection memory board or cartridge.

              The following status values are supported:

                 other(1):
                   The condition of this memory board or cartridge
                   could not be determined.

                 ok(2):
                   The memory board or cartridge is operating normally.

                 degraded(3):
                   The memory board or cartridge is in an error state.
                   Check for correct memory installation and that the
                   board has been inserted properly."
        ::= { cpqHeResMemBoardEntry 8 }

    cpqHeResMemBoardHotPlug OBJECT-TYPE
        SYNTAX  INTEGER {
            other(1),
            nonHotPluggable(2),
            hotPluggable(3)
            }
        ACCESS  read-only
        STATUS  mandatory
        DESCRIPTION
            "This indicates if the memory board is capable of being
            removed and/or inserted while the system is in an
            operational state.

            The following states are supported:

            other(1)
              The state could not be determined or the system does not
              support Advanced Memory Protection.

            nonHotPluggable(2)
              The memory board or cartridge is not hot plug capable.

            hotPluggable(3)
              The memory board or cartridge is hot plug capable and can be
              removed if the system is operating in a redundant state.  A
              memory board or cartridge may be added to an empty bay."
        ::= { cpqHeResMemBoardEntry 9 }

-- ****************************************************************************
--   Health MIB Advanced Memory Protection Memory Module Group
--   =========================================================
--
-- The compaq enterprise               (1.3.6.1.4.1.232)
--      cpqHealth Group                (1.3.6.1.4.1.232.6)
--       cpqHeComponent Group          (1.3.6.1.4.1.232.6.2)
--        cpqHeResilientMemory Group   (1.3.6.1.4.1.232.6.2.14)
--         cpqHeResMemModuleTable      (1.3.6.1.4.1.232.6.2.14.11)
--          cpqHeResMemModuleEntry     (1.3.6.1.4.1.232.6.2.14.11.1)
--
-- ****************************************************************************

    cpqHeResMemModuleTable OBJECT-TYPE
        SYNTAX  SEQUENCE OF CpqHeResMemModuleEntry
        ACCESS  not-accessible
        STATUS  mandatory
        DESCRIPTION
            "A table of memory module descriptions."
        ::= { cpqHeResilientMemory 11 }

    cpqHeResMemModuleEntry OBJECT-TYPE
        SYNTAX  CpqHeResMemModuleEntry
        ACCESS  not-accessible
        STATUS  mandatory 
        DESCRIPTION
            "A memory module description."
        INDEX   { cpqHeResMemBoardIndex, cpqHeResMemModuleIndex }
        ::= { cpqHeResMemModuleTable 1 }

    CpqHeResMemModuleEntry ::= SEQUENCE {
        cpqHeResMemBoardIndex            INTEGER,
        cpqHeResMemModuleIndex           INTEGER,
        cpqHeResMemModuleSparePartNo     DisplayString,
        cpqHeResMemModuleStatus          INTEGER,
        cpqHeResMemModuleCondition       INTEGER,
        cpqHeResMemModuleSpd             OCTET STRING
    }

    cpqHeResMemBoardIndex OBJECT-TYPE
        SYNTAX  INTEGER
        ACCESS  read-only
        STATUS  mandatory
        DESCRIPTION
            "The slot in which the memory board or cartridge is installed.

            A value of 0 indicates memory installed directly on the
            system board."
        ::= { cpqHeResMemModuleEntry 1 }

    cpqHeResMemModuleIndex OBJECT-TYPE
        SYNTAX  INTEGER
        ACCESS  read-only
        STATUS  mandatory
        DESCRIPTION
            "The memory module number."
        ::= { cpqHeResMemModuleEntry 2 }

    cpqHeResMemModuleSparePartNo OBJECT-TYPE
        SYNTAX  DisplayString (SIZE (0..32))
        ACCESS  read-only
        STATUS  mandatory
        DESCRIPTION
             "The memory module's manufacturer part number.

              This field will be a null (size 0) string if the manufacturer
              part number is not available."
        ::= { cpqHeResMemModuleEntry 3 }

    cpqHeResMemModuleStatus OBJECT-TYPE
        SYNTAX  INTEGER {
            other(1),
            notPresent(2),
            present(3),
            good(4),
            add(5),
            upgrade(6),
            missing(7),
            doesNotMatch(8),
            notSupported(9),
            badConfig(10),
            degraded(11)
        }
        ACCESS  read-only
        STATUS  mandatory
        DESCRIPTION
             "This provides the current status of the correctable memory
              errors for this memory module.

              The following status values are supported:

                 other(1):
                   The status is unknown or could not be determined.

                 notPresent(2):
                   The memory module is not present or is un-initialized.

                 present(3):
                   The memory module is present but not in use.

                 good(4):
                   The memory module is present and in use.  The corrected
                   error threshold has not been exceeded.

                 add(5):
                   The memory module has been added, but is not yet in use.

                 upgraded(6):
                   The memory module has been upgraded, but the memory is not
                   yet in use.

                 missing(7):
                   An expected memory module is missing.

                 doesNotMatch(8):
                   The memory module does not match the other memory modules
                   within the bank.

                 notSupported(9):
                   The memory module is not supported.

                 badConfig(10):
                   The memory module violates the add/upgrade configuration
                   rules.

                 degraded(11):
                   The memory module's correctable error count has exceeded
                   threshold."
        ::= { cpqHeResMemModuleEntry 4 }

    cpqHeResMemModuleCondition OBJECT-TYPE
        SYNTAX  INTEGER {
            other(1),
            ok(2),
            degraded(3)
        }
        ACCESS  read-only
        STATUS  mandatory
        DESCRIPTION
             "This provides the current status of the correctable memory
              errors for this memory module.

              The following status values are supported:

                 other(1):
                   ECC is not supported on this memory module or the
                   condition could not be determined.

                 ok(2):
                   The memory module is operating normally.

                 degraded(3):
                   The memory module is correctable error count has exceeded
                   threshold or a configuration error has been detected."
        ::= { cpqHeResMemModuleEntry 5 }

    cpqHeResMemModuleSpd OBJECT-TYPE
        SYNTAX  OCTET STRING (SIZE (0..256))
        ACCESS  read-only
        STATUS  mandatory
        DESCRIPTION
            "This is the raw Serial Presence Detect information contained
            in the memory module.

            If the SPD information is not available, this item will be empty."
        ::= { cpqHeResMemModuleEntry 6 }

-- ****************************************************************************
--   Health MIB Advanced Memory Protection Board Group
--   =================================================
--
-- The compaq enterprise               (1.3.6.1.4.1.232)
--      cpqHealth Group                (1.3.6.1.4.1.232.6)
--       cpqHeComponent Group          (1.3.6.1.4.1.232.6.2)
--        cpqHeResilientMemory Group   (1.3.6.1.4.1.232.6.2.14)
--         cpqHeResMem2BoardTable       (1.3.6.1.4.1.232.6.2.14.12)
--          cpqHeResMem2BoardEntry      (1.3.6.1.4.1.232.6.2.14.12.1)
--
-- ****************************************************************************

    cpqHeResMem2BoardTable OBJECT-TYPE
        SYNTAX  SEQUENCE OF CpqHeResMem2BoardEntry
        ACCESS  not-accessible
        STATUS  mandatory
        DESCRIPTION
            "A table of memory board or cartridge descriptions in Advanced
            Memory Protection systems."
        ::= { cpqHeResilientMemory 12 }

    cpqHeResMem2BoardEntry OBJECT-TYPE
        SYNTAX  CpqHeResMem2BoardEntry
        ACCESS  not-accessible
        STATUS  mandatory
        DESCRIPTION
            "A memory board or cartridge or CPU based Memory Board description."
        INDEX   { cpqHeResMem2BoardIndex }
        ::= { cpqHeResMem2BoardTable 1 }

    CpqHeResMem2BoardEntry ::= SEQUENCE {
        cpqHeResMem2BoardIndex       INTEGER,
        cpqHeResMem2BoardSlotNum       INTEGER,
        cpqHeResMem2BoardCpuNum       INTEGER,
        cpqHeResMem2BoardRiserNum       INTEGER,
        cpqHeResMem2BoardOnlineStatus    INTEGER,
        cpqHeResMem2BoardErrorStatus     INTEGER,
        cpqHeResMem2BoardLocked          INTEGER,
        cpqHeResMem2BoardNumSockets      INTEGER,
        cpqHeResMem2BoardOsMemSize       INTEGER,
        cpqHeResMem2BoardTotalMemSize    INTEGER,
        cpqHeResMem2BoardCondition       INTEGER,
        cpqHeResMem2BoardHotPlug         INTEGER,
        cpqHeResMem2BoardOperatingFrequency INTEGER,
        cpqHeResMem2BoardOperatingVoltage INTEGER
    }

    cpqHeResMem2BoardIndex OBJECT-TYPE
        SYNTAX  INTEGER
        ACCESS  read-only
        STATUS  mandatory
        DESCRIPTION
            "This will represent the unique memory board or cartridge or riser."
        ::= { cpqHeResMem2BoardEntry 1 }


    cpqHeResMem2BoardSlotNum OBJECT-TYPE
        SYNTAX  INTEGER
        ACCESS  read-only
        STATUS  mandatory
        DESCRIPTION
            "The slot in which the memory board or cartridge is installed."
        ::= { cpqHeResMem2BoardEntry 2 }

    cpqHeResMem2BoardCpuNum OBJECT-TYPE
        SYNTAX  INTEGER
        ACCESS  read-only
        STATUS  mandatory
        DESCRIPTION
            "The Processor Number to which the memory Riser belongs. Value 0 means memory is not CPU based."
        ::= { cpqHeResMem2BoardEntry 3 }

    cpqHeResMem2BoardRiserNum OBJECT-TYPE
        SYNTAX  INTEGER
        ACCESS  read-only
        STATUS  mandatory
        DESCRIPTION
            "The Riser Number on the Processor."
        ::= { cpqHeResMem2BoardEntry 4 }

    cpqHeResMem2BoardOnlineStatus OBJECT-TYPE
        SYNTAX  INTEGER {
            other(1),
            present(2),
            absent(3)
        }
        ACCESS  read-only
        STATUS  mandatory
        DESCRIPTION
            "The online status of the Advanced Memory Protection board or 
              cartridge or riser.

            The following status values are supported:

                 other(1)
                   The value is unsupported or could not be determined.

                 present(2)
                   The board or cartridge or riser has memory and is currently online.

                 absent(3)
                   The board or cartridge or riser is missing or offline."
        ::= { cpqHeResMem2BoardEntry 5 }

    cpqHeResMem2BoardErrorStatus OBJECT-TYPE
        SYNTAX  INTEGER {
            other(1),
            noError(2),
            dimmEccError(3),
            unlockError(4),
            configError(5),
            busError(6),
            powerError(7),
            advancedEcc(8),
            onlineSpare(9),
            mirrored(10),
            mirroredDimmError(11),
            memoryRaid(12),
            raidDimmError(13),
            lockStep(14),
            lockStepError(15)
        }
        ACCESS  read-only
        STATUS  mandatory
        DESCRIPTION
            "The error status of the Advanced Memory Protection board or
            Cartridge or riser.

            The following status values are supported:

                 other(1)
                   The value is unsupported or could not be determined.

                 noError(2)
                   The board or cartridge or riser is configured and operating correctly.

                 dimmEccError(3)
                   The board or cartridge or riser has at least one DIMM ECC error.

                 unlockError(4)
                   The board or cartridge or riser is unlocked when it should not be.
                   Please insure the board of cartridge is locked.

                 configError(5)
                   The board or cartridge or riser has a bad memory configuration.
                   Please insure all memory modules are of the correct type,
                   speed, latency, etc.

                 busError(6)
                   The board or cartridge or riser has a memory bus error.
                   Please insure all memory modules are of the correct type,
                   speed, latency, etc.  Also insure the cartridge is inserted
                   properly.

                 powerError(7)
                   The board or cartridge or riser has power error.
                   Please insure all memory modules are of the correct type,
                   speed, latency, etc.  Also insure the cartridge is inserted
                   properly.

                 advancedEcc(8),
                   The board or cartridge or riser is configured for advanced Ecc mode.

                 onlineSpare(9),
                   The board or cartridge or riser is configured for Online Spare mode.

                 mirrored(10),
                   The board or cartridge or riser is configured for mirrored mode.

                 mirroredDimmError(11),
                   The board or cartridge or riser has a mirrored Dimm error.

                 memoryRaid(12),
                   The board or cartridge or riser is configured for memory raid mode.

                 raidDimmError(13)
                   The board or cartridge or riser has a raid Dimm error.

                 lockStep(14),
                   The board or cartridge or riser is configured for lockStep mode.

                 lockStepError(15)
                   The board or cartridge or riser has a lockStep Dimm error."
        ::= { cpqHeResMem2BoardEntry 6 }

    cpqHeResMem2BoardLocked OBJECT-TYPE
        SYNTAX  INTEGER {
            other(1),
            unlocked(2),
            locked(3)
        }
        ACCESS  read-only
        STATUS  mandatory
        DESCRIPTION
            "The locked state of the Advanced Memory Protection board or
            Cartridge or riser.

            The following status values are supported:

                 other(1)
                   The value is unsupported or could not be determined.  If the
                   system does not support hot plugging of the board or
                   cartridge or riser, then this value will be returned.

                 unlocked(2)
                   The board or cartridge or riser is currently unlocked and may be
                   removed.

                 locked(3)
                   The board or cartridge or riser is currently locked and may not be
                   removed."
        ::= { cpqHeResMem2BoardEntry 7 }

    cpqHeResMem2BoardNumSockets OBJECT-TYPE
        SYNTAX  INTEGER
        ACCESS  read-only
        STATUS  mandatory
        DESCRIPTION
            "The total number of memory sockets for this memory board or
            Cartridge or riser.

            If this value could not be determined, or if the board or
            Cartridge or riser has been removed, this value will be -1."
        ::= { cpqHeResMem2BoardEntry 8 }

    cpqHeResMem2BoardOsMemSize OBJECT-TYPE
        SYNTAX  INTEGER
        ACCESS  read-only
        STATUS  mandatory
        DESCRIPTION
            "This value specifies the size of memory for this board or
            cartridge or riser as seen by the Operating System in MB (1 MB =
            1048576 bytes).

            If this system does not support Advanced Memory Protection or this
            value cannot be determined, then a value of 0 will be returned."
        ::= { cpqHeResMem2BoardEntry 9 }

    cpqHeResMem2BoardTotalMemSize OBJECT-TYPE
        SYNTAX  INTEGER
        ACCESS  read-only
        STATUS  mandatory
        DESCRIPTION
            "This value specifies the size of memory for this board or
            Cartridge or riser including memory seen by the Operating System and
            the memory used for spare, mirrored, or XOR configurations
            in MB (1 MB = 1048576 bytes).

            If this system does not support Advanced Memory Protection or this
            value cannot be determined, then a value of 0 will be returned."
        ::= { cpqHeResMem2BoardEntry 10 }

    cpqHeResMem2BoardCondition OBJECT-TYPE
        SYNTAX  INTEGER {
            other(1),
            ok(2),
            degraded(3)
        }
        ACCESS  read-only
        STATUS  mandatory
        DESCRIPTION
             "This provides the current status of the Advanced Memory
              Protection memory board or cartridge or riser.

              The following status values are supported:

                 other(1):
                   The condition of this memory board or cartridge or riser
                   could not be determined.

                 ok(2):
                   The memory board or cartridge or riser is operating normally.

                 degraded(3):
                   The memory board or cartridge or riser is in an error state.
                   Check for correct memory installation and that the
                   board has been inserted properly."
        ::= { cpqHeResMem2BoardEntry 11 }

    cpqHeResMem2BoardHotPlug OBJECT-TYPE
        SYNTAX  INTEGER {
            other(1),
            nonHotPluggable(2),
            hotPluggable(3)
            }
        ACCESS  read-only
        STATUS  mandatory
        DESCRIPTION
            "This indicates if the memory board is capable of being
            removed and/or inserted while the system is in an
            operational state.

            The following states are supported:

            other(1)
              The state could not be determined or the system does not
              support Advanced Memory Protection.

            nonHotPluggable(2)
              The memory board or cartridge or riser is not hot plug capable.

            hotPluggable(3)
              The memory board or cartridge or riser is hot plug capable and can be
              removed if the system is operating in a redundant state.  A
              memory board or cartridge or riser may be added to an empty bay."
        ::= { cpqHeResMem2BoardEntry 12}

    cpqHeResMem2BoardOperatingFrequency OBJECT-TYPE
        SYNTAX  INTEGER
        ACCESS  read-only
        STATUS  mandatory
        DESCRIPTION
            "This value specifies the operational memory frequency for 
            this board or Cartridge or riser in MHz."
        ::= { cpqHeResMem2BoardEntry 13 }

    cpqHeResMem2BoardOperatingVoltage OBJECT-TYPE
        SYNTAX  INTEGER
        ACCESS  read-only
        STATUS  mandatory
        DESCRIPTION
            "This value specifies the operational memory voltage for 
            this board or Cartridge or riser in millivolts."
        ::= { cpqHeResMem2BoardEntry 14 }

-- ****************************************************************************
--   Health MIB Advanced Memory Protection Memory Module Group
--   =========================================================
--
-- The compaq enterprise               (1.3.6.1.4.1.232)
--      cpqHealth Group                (1.3.6.1.4.1.232.6)
--       cpqHeComponent Group          (1.3.6.1.4.1.232.6.2)
--        cpqHeResilientMemory Group   (1.3.6.1.4.1.232.6.2.14)
--         cpqHeResMem2ModuleTable     (1.3.6.1.4.1.232.6.2.14.13)
--          cpqHeResMem2ModuleEntry     (1.3.6.1.4.1.232.6.2.14.13.1)
--
-- ****************************************************************************

    cpqHeResMem2ModuleTable OBJECT-TYPE
        SYNTAX  SEQUENCE OF CpqHeResMem2ModuleEntry
        ACCESS  not-accessible
        STATUS  mandatory
        DESCRIPTION
            "A table of memory module descriptions."
        ::= { cpqHeResilientMemory 13 }

    cpqHeResMem2ModuleEntry OBJECT-TYPE
        SYNTAX  CpqHeResMem2ModuleEntry
        ACCESS  not-accessible
        STATUS  mandatory 
        DESCRIPTION
            "A memory module description."
        INDEX   { cpqHeResMem2Module }
        ::= { cpqHeResMem2ModuleTable 1 }

    CpqHeResMem2ModuleEntry ::= SEQUENCE {
        cpqHeResMem2Module            INTEGER,
        cpqHeResMem2BoardNum            INTEGER,
        cpqHeResMem2CpuNum            INTEGER,
        cpqHeResMem2RiserNum            INTEGER,
        cpqHeResMem2ModuleNum            INTEGER,
        cpqHeResMem2ModuleSize            INTEGER,
        cpqHeResMem2ModuleType            INTEGER,
        cpqHeResMem2ModuleTechnology      INTEGER,
        cpqHeResMem2ModuleManufacturer    DisplayString,
        cpqHeResMem2ModulePartNo          DisplayString,
        cpqHeResMem2ModuleDate            OCTET STRING,
        cpqHeResMem2ModuleSerialNo        DisplayString,
        cpqHeResMem2ModuleHwLocation      DisplayString,
        cpqHeResMem2ModuleFrequency       INTEGER,
        cpqHeResMem2ModuleCellTablePtr    INTEGER,
        cpqHeResMem2ModuleCellStatus      INTEGER,
        cpqHeResMem2ModulePartNoMfgr      DisplayString,
        cpqHeResMem2ModuleSerialNoMfgr    DisplayString,
        cpqHeResMem2ModuleStatus          INTEGER,
        cpqHeResMem2ModuleCondition       INTEGER,
        cpqHeResMem2ModuleSpd             OCTET STRING,
        cpqHeResMem2ModuleSmartMemory     INTEGER,
        cpqHeResMem2ModuleMinVoltage      INTEGER,
        cpqHeResMem2ModuleRanks           INTEGER
    }

    cpqHeResMem2Module OBJECT-TYPE
        SYNTAX  INTEGER
        ACCESS  read-only
        STATUS  mandatory
        DESCRIPTION
            "This will represent the unique memory DIMM on 
              memory board or cartridge or riser. "
        ::= { cpqHeResMem2ModuleEntry 1 }

    cpqHeResMem2BoardNum OBJECT-TYPE
        SYNTAX  INTEGER
        ACCESS  read-only
        STATUS  mandatory
        DESCRIPTION
            "The slot in which the memory board or cartridge is installed.

            A value of 0 indicates memory installed directly on the
            system board."
        ::= { cpqHeResMem2ModuleEntry 2 }

    cpqHeResMem2CpuNum OBJECT-TYPE
        SYNTAX  INTEGER
        ACCESS  read-only
        STATUS  mandatory
        DESCRIPTION
            "The memory module CPU number. Value 0 means memory is not Processor based."
        ::= { cpqHeResMem2ModuleEntry 3 }

    cpqHeResMem2RiserNum OBJECT-TYPE
        SYNTAX  INTEGER
        ACCESS  read-only
        STATUS  mandatory
        DESCRIPTION
            "The memory module rasier number."
        ::= { cpqHeResMem2ModuleEntry 4 }

    cpqHeResMem2ModuleNum OBJECT-TYPE
        SYNTAX  INTEGER
        ACCESS  read-only
        STATUS  mandatory
        DESCRIPTION
            "The memory module number."
        ::= { cpqHeResMem2ModuleEntry 5 }

    cpqHeResMem2ModuleSize OBJECT-TYPE
        SYNTAX  INTEGER (0..2147483647)
        ACCESS  read-only
        STATUS  mandatory
        DESCRIPTION
            "Module memory size in kilobytes.  A kilobyte of memory is
            defined as 1024 bytes.

            A size of 0 indicates the module is not present."
        ::= { cpqHeResMem2ModuleEntry 6 }

    cpqHeResMem2ModuleType OBJECT-TYPE 
        SYNTAX  INTEGER {
                other(1),
                board(2),
                cpqSingleWidthModule(3),
                cpqDoubleWidthModule(4),
                simm(5),
                pcmcia(6),
                compaq-specific(7), 
                dimm(8),
                smallOutlineDimm(9),
                rimm(10),
                srimm(11),
                fb-dimm(12),
                dimmddr(13),
                dimmddr2(14),
                dimmddr3(15),
                dimmfbd2(16),
                fb-dimmddr2(17),
                fb-dimmddr3(18),
		dimmddr4(19)
             }
        ACCESS  read-only
        STATUS  mandatory
        DESCRIPTION
            "Type of memory module installed.  The value other(1) will be
             given if the type is not known.  The value board(2) will be
             given if the memory module is permanently mounted (not modular)
             on a system board or memory expansion board."
        ::= { cpqHeResMem2ModuleEntry 7 }

    cpqHeResMem2ModuleTechnology OBJECT-TYPE
        SYNTAX  INTEGER {
                other(1),
                fastPageMode(2),
                edoPageMode(3),
                burstEdoPageMode(4),
                synchronous(5),
                rdram(6),
                rdimm(7),
                udimm(8),
                lrdimm(9)
             }
        ACCESS  read-only
        STATUS  mandatory
        DESCRIPTION
            "Technology type of memory module installed.  The value other(1)
             will be given if the technology is not known."
        ::= { cpqHeResMem2ModuleEntry 8 }

    cpqHeResMem2ModuleManufacturer OBJECT-TYPE
        SYNTAX  DisplayString (SIZE (0..255))
        ACCESS  read-only
        STATUS  mandatory
        DESCRIPTION
             "The memory module's manufacturer name.

              This field will be a null (size 0) string if the manufacturer
              name is not available."
        ::= { cpqHeResMem2ModuleEntry 9 }

    cpqHeResMem2ModulePartNo OBJECT-TYPE
        SYNTAX  DisplayString (SIZE (0..255))
        ACCESS  read-only
        STATUS  mandatory
        DESCRIPTION
             "The memory module's manufacturer part number.

              This field will be a null (size 0) string if the manufacturer
              part number is not available."
        ::= { cpqHeResMem2ModuleEntry 10 }

    cpqHeResMem2ModuleDate OBJECT-TYPE
        SYNTAX  OCTET STRING (SIZE (7))
        ACCESS  read-only
        STATUS  mandatory
        DESCRIPTION
             "The memory module date of manufacture.

             field  octets  contents                  range
             =====  ======  ======================    ========
               1     1-2    year                      0..65536
               2       3    month                     1..12
               3       4    day                       1..31
               4       5    hour                      0..23
               5       6    minute                    0..59
               6       7    second                    0..60
                           (use 60 for leap-second)

             This field will be set to year = 0 if the date of manufacture
             is not available.  The hour, minute, and second fields will
             always be set to 0."
        ::= { cpqHeResMem2ModuleEntry 11 }

    cpqHeResMem2ModuleSerialNo OBJECT-TYPE
        SYNTAX  DisplayString (SIZE (0..255))
        ACCESS  read-write
        STATUS  mandatory
        DESCRIPTION
             "The memory module's serial number.

              This field will be a null (size 0) string if the serial number
              is not available."
        ::= { cpqHeResMem2ModuleEntry 12 }

    cpqHeResMem2ModuleHwLocation OBJECT-TYPE
        SYNTAX  DisplayString (SIZE (0..255))
        ACCESS  read-only
        STATUS  optional
        DESCRIPTION
            "A text description of the hardware location, on complex
             multi SBB hardware only, for the memory module.
             A NULL string indicates that the hardware location could not
             be determined or is irrelevant."
        ::= { cpqHeResMem2ModuleEntry 13 }


    cpqHeResMem2ModuleFrequency OBJECT-TYPE
        SYNTAX  INTEGER (0..65535)
        ACCESS  read-only
        STATUS  mandatory
        DESCRIPTION
            "The memory module maximum frequency in MHz.  The value zero 
             (0) will be given if the module frequency cannot be determined."
        ::= { cpqHeResMem2ModuleEntry 14 }

    cpqHeResMem2ModuleCellTablePtr OBJECT-TYPE
        SYNTAX  INTEGER (0..15)
        ACCESS  read-only
        STATUS  optional
        DESCRIPTION
            "Index for the cell in cpqSeCellTable where the memory board is
             installed."
        ::= { cpqHeResMem2ModuleEntry 15 }

    cpqHeResMem2ModuleCellStatus OBJECT-TYPE
        SYNTAX  INTEGER {
            other(1),
            ok(2),
            deconfigured(3)
        }
        ACCESS  read-only
        STATUS  optional
        DESCRIPTION
             "This provides the current status for this memory module.

              The following status values are supported:

                 other(1):
                   The memory module status is not available

                 ok(2):
                   The memory module is active

                 deconfigured(3):
                   The memory module is not ready"
        ::= { cpqHeResMem2ModuleEntry 16 }


    cpqHeResMem2ModulePartNoMfgr OBJECT-TYPE
        SYNTAX  DisplayString (SIZE (0..255))
        ACCESS  read-only
        STATUS  optional
        DESCRIPTION
             "The memory module's manufacturer's part number.

              This field will be a null (size 0) string if the manufacturer
              part number is not available."
        ::= { cpqHeResMem2ModuleEntry 17 }

    cpqHeResMem2ModuleSerialNoMfgr OBJECT-TYPE
        SYNTAX  DisplayString (SIZE (0..255))
        ACCESS  read-only
        STATUS  optional
        DESCRIPTION
             "The memory module's manufacturer's serial number.

              This field will be a null (size 0) string if the manufacturer
              serial number is not available."
        ::= { cpqHeResMem2ModuleEntry 18 }


    cpqHeResMem2ModuleStatus OBJECT-TYPE
        SYNTAX  INTEGER {
            other(1),
            notPresent(2),
            present(3),
            good(4),
            add(5),
            upgrade(6),
            missing(7),
            doesNotMatch(8),
            notSupported(9),
            badConfig(10),
            degraded(11),
            spare(12),
            partial(13)
        }
        ACCESS  read-only
        STATUS  mandatory
        DESCRIPTION
             "This provides the current status of the correctable memory
              errors for this memory module.

              The following status values are supported:

                 other(1):
                   The status is unknown or could not be determined.

                 notPresent(2):
                   The memory module is not present or is un-initialized.

                 present(3):
                   The memory module is present but not in use.

                 good(4):
                   The memory module is present and in use.  The corrected
                   error threshold has not been exceeded.

                 add(5):
                   The memory module has been added, but is not yet in use.

                 upgraded(6):
                   The memory module has been upgraded, but the memory is not
                   yet in use.

                 missing(7):
                   An expected memory module is missing.

                 doesNotMatch(8):
                   The memory module does not match the other memory modules
                   within the bank.

                 notSupported(9):
                   The memory module is not supported.

                 badConfig(10):
                   The memory module violates the add/upgrade configuration
                   rules.

                 degraded(11):
                   The memory module's correctable error count has exceeded
                   threshold.

                 spare(12):
                   The memory module is configured as a spare.

                 partial(13):
                   The memory module is present and is partially in use."

        ::= { cpqHeResMem2ModuleEntry 19 }

    cpqHeResMem2ModuleCondition OBJECT-TYPE
        SYNTAX  INTEGER {
            other(1),
            ok(2),
            degraded(3),
            degradedModuleIndexUnknown(4)
        }
        ACCESS  read-only
        STATUS  mandatory
        DESCRIPTION
             "This provides the current status of the correctable memory
              errors for this memory module.

              The following status values are supported:

                 other(1):
                   ECC is not supported on this memory module or the
                   condition could not be determined.

                 ok(2):
                   The memory module is operating normally.

                 degraded(3):
                   The memory module is correctable error count has exceeded
                   threshold or a configuration error has been detected.

                 degradedModuleIndexUnknown(4):
                   The correctable error count has exceeded threshold.
                   The module number not available."
        ::= { cpqHeResMem2ModuleEntry 20 }

    cpqHeResMem2ModuleSpd OBJECT-TYPE
        SYNTAX  OCTET STRING (SIZE (0..256))
        ACCESS  read-only
        STATUS  mandatory
        DESCRIPTION
            "This is the raw Serial Presence Detect information contained
            in the memory module.

            If the SPD information is not available, this item will be empty."
        ::= { cpqHeResMem2ModuleEntry 21 }

    cpqHeResMem2ModuleSmartMemory OBJECT-TYPE
        SYNTAX  INTEGER {
            other(1),
            notHPSmartMemory(2),
            isHPSmartMemory(3)
        }
        ACCESS  read-only
        STATUS  mandatory
        DESCRIPTION
             "This indicates whether the DIMM slot is populated with an HP 
              Smart Memory DIMM.

              The following values are supported:

                 other(1):
                   HP SmartMemory not supported in this device.

                 notHPSmartMemory(2):
                   HP SmartMemory is NOT installed in DIMM slot (includes 
                   the case where the DIMM slot is not populated).
 
                 isHPSmartMemory(3):
                   HP SmartMemory is installed in DIMM slot."

        ::= { cpqHeResMem2ModuleEntry 22 }

    cpqHeResMem2ModuleMinVoltage OBJECT-TYPE
        SYNTAX  INTEGER (0..65535)
        ACCESS  read-only
        STATUS  mandatory
        DESCRIPTION
             "This provides the minimum voltage needed for the module to 
              operate, in millivolts."
        ::= { cpqHeResMem2ModuleEntry 23 }

    cpqHeResMem2ModuleRanks OBJECT-TYPE
        SYNTAX  INTEGER (0..65535)
        ACCESS  read-only
        STATUS  mandatory
        DESCRIPTION
             "This provides the number of physical ranks on the module."
        ::= { cpqHeResMem2ModuleEntry 24 }


-- ****************************************************************************
--   Health MIB Power Meter Group
--   ========================================
--
-- The compaq enterprise               (1.3.6.1.4.1.232)
--      cpqHealth Group                (1.3.6.1.4.1.232.6)
--       cpqHeComponent Group          (1.3.6.1.4.1.232.6.2)
--        cpqHePowerMeter Group        (1.3.6.1.4.1.232.6.2.15)
--
--  The cpqHePowerMeter group describes the Server's power consumption read
--  
--
--  Implementation of the cpqHePowerMeter group is mandatory for all
--  platform that support Power Meter.
--
-- ****************************************************************************

    cpqHePowerMeterSupport OBJECT-TYPE
        SYNTAX  INTEGER {
            other(1), 
            supported(2),
            unsupported(3)            
        }
        ACCESS  read-only
        STATUS  mandatory
        DESCRIPTION
            "This value specifies whether Power Meter is supported  
             by this Server .

             The following values are supported:

             other(1)
               Could not read the Power Meter status.

             supported(2)
               This system support Power Meter.

             unsupported(3)
               This system does not support Power Meter."
        ::= { cpqHePowerMeter 1}


    cpqHePowerMeterStatus OBJECT-TYPE
        SYNTAX  INTEGER {
            other(1), 
            present(2),
            absent(3)            
        }
        ACCESS  read-only
        STATUS  mandatory
        DESCRIPTION
            "This value specifies whether Power Meter reading is supported  
             by this Server .

             The following values are supported:

             other(1)
               Could not read the Power Meter status.

             present(2)
               The Power Meter data is available.

             absent(3)
               The Power Meter data is not available at this time."
        ::= { cpqHePowerMeter 2}


    cpqHePowerMeterCurrReading OBJECT-TYPE
        SYNTAX  INTEGER
        ACCESS  read-only
        STATUS  mandatory
        DESCRIPTION
            " This is the current Power Meter reading in Watts.
              This value shows the most recent power reading if available. 
              On systems without Power Meter support, this value will be -1."
        ::= { cpqHePowerMeter 3 }

    cpqHePowerMeterPrevReading OBJECT-TYPE
        SYNTAX  INTEGER
        ACCESS  read-only
        STATUS  mandatory
        DESCRIPTION
            " This is the previous Power Meter reading in Watts. 
              This value shows previous power reading if available. 
              On systems without Power Meter support, this value will be -1."
        ::= { cpqHePowerMeter 4 }

--*****************************************************************************
--   Health MIB Hardware BIOS Group
--   ===============================
--
-- The compaq enterprise               (1.3.6.1.4.1.232)
--      cpqHealth Group                (1.3.6.1.4.1.232.6)
--       cpqHeComponent Group          (1.3.6.1.4.1.232.6.2)
--        cpqHeHWBios Group            (1.3.6.1.4.1.232.6.2.16)
--
--  The cpqHeHWBios group describes the Server's Hardware BIOS information
--
--
-- ****************************************************************************

     cpqHeHWBiosCondition OBJECT-TYPE
        SYNTAX  INTEGER {
            other(1),
            ok(2),
            degraded(3),
            failed(4)
            }
        ACCESS  read-only
        STATUS  mandatory
        DESCRIPTION
            "This value indicates an error has been detected  during Pre-OS Test (POST) or
              during initial hardware initialization. Typically, this will be a hardware interlock
              not closed due to an adapter or cable not properly seated in the slot. The first
              action is to review the iLO Event Log and iLO Integrated Management Log (IML)
              for a new event. If no entries found, the  server will usually require a physical 
              inspection to identify the source of the issue by observing the external and 
              internal hardware status LEDs.


            This value will be one of the following:
            other(1)
              There is no data available to support the cpqHeHWBiosCondition.

            ok(2)
              The primary server hardware is operational.

            degraded(3)
              A non-fatal condition detected. Review iLO Event and Integrated Management Logs.

            failed(4)
              A fatal condition detected during POST or prior to hardware power on."
        ::= { cpqHeHWBios 1 }


-- ****************************************************************************
--   Health MIB System Backup Battery Group 
--   ============================================
--
-- The compaq enterprise               (1.3.6.1.4.1.232)
--      cpqHealth Group                (1.3.6.1.4.1.232.6)
--       cpqHeComponent Group          (1.3.6.1.4.1.232.6.2)
--        cpqHeSysBackupBattery Group  (1.3.6.1.4.1.232.6.2.17)
--
--  The cpqHeSysBackupBattery group contains management information about
--  HP Smart Storage Batteries.
-- 
--  Implementation of the cpqHeSysBackupBattery group is mandatory for all
--  agents that support the Server Health MIB.
--
-- ****************************************************************************
    cpqHeSysBackupBatteryCondition OBJECT-TYPE
        SYNTAX  INTEGER {
            other(1),
            ok(2),
            degraded(3),
            failed(4)
            }
        ACCESS  read-only
        STATUS  mandatory
        DESCRIPTION
            "This value specifies the overall condition of the battery 
             backup sub-system."
        ::= { cpqHeSysBackupBattery 1 }

-- ****************************************************************************
--   Health MIB System Battery Table
--   ============================================
--
-- The compaq enterprise               (1.3.6.1.4.1.232)
--      cpqHealth Group                (1.3.6.1.4.1.232.6)
--       cpqHeComponent Group          (1.3.6.1.4.1.232.6.2)
--        cpqHeSysBackupBattery Group  (1.3.6.1.4.1.232.6.2.17)
--         cpqHeSysBattery Table       (1.3.6.1.4.1.232.6.2.17.2)
--
-- ****************************************************************************

    cpqHeSysBatteryTable OBJECT-TYPE
        SYNTAX  SEQUENCE OF CpqHeSysBatteryEntry
        ACCESS  not-accessible
        STATUS  mandatory
        DESCRIPTION
            "A table of battery entries."
        ::= { cpqHeSysBackupBattery 2}

    cpqHeSysBatteryEntry OBJECT-TYPE
        SYNTAX  CpqHeSysBatteryEntry
        ACCESS  not-accessible
        STATUS  mandatory
        DESCRIPTION
            "A System Backup Battery Entry."
        INDEX   { cpqHeSysBatteryChassis, cpqHeSysBatteryIndex }
        ::= { cpqHeSysBatteryTable 1 }

    CpqHeSysBatteryEntry ::= SEQUENCE {
        cpqHeSysBatteryChassis             INTEGER,
        cpqHeSysBatteryIndex               INTEGER,
        cpqHeSysBatteryPresent             INTEGER,
        cpqHeSysBatteryCondition           INTEGER,
        cpqHeSysBatteryStatus              INTEGER,
        cpqHeSysBatteryCapacityMaximum     INTEGER,
        cpqHeSysBatteryProductName         DisplayString,
        cpqHeSysBatteryModel               DisplayString,
        cpqHeSysBatterySerialNumber        DisplayString,
        cpqHeSysBatteryFirmwareRev         DisplayString,
        cpqHeSysBatterySparePartNum        DisplayString
}

  cpqHeSysBatteryChassis OBJECT-TYPE
        SYNTAX  INTEGER (0..255)
        ACCESS  read-only
        STATUS  mandatory
        DESCRIPTION
            "The system chassis number." 
        ::= { cpqHeSysBatteryEntry 1 }

    cpqHeSysBatteryIndex OBJECT-TYPE
        SYNTAX  INTEGER (1..255)
        ACCESS  read-only
        STATUS  mandatory
        DESCRIPTION
            "The battery index number within this chassis."
        ::= { cpqHeSysBatteryEntry 2 }

    cpqHeSysBatteryPresent OBJECT-TYPE
        SYNTAX  INTEGER {
            other(1),
            absent(2),
            present(3)
            }
        ACCESS  read-only
        STATUS  mandatory
        DESCRIPTION
            "Indicates whether the backup battery is present in the chassis."
        ::= { cpqHeSysBatteryEntry 3 }

    cpqHeSysBatteryCondition OBJECT-TYPE
        SYNTAX  INTEGER {
            other(1),
            ok(2),
            degraded(3),
            failed(4)
            }
        ACCESS  read-only
        STATUS  mandatory
        DESCRIPTION
            "The condition of the backup battery.

            This value will be one of the following:

            other(1)
              The status could not be determined or not present.

            ok(2)
              The battery is operating normally.

            degraded(3)
              The battery is degraded.

            failed(4)
              The battery has stopped responding or has shutdown
              in order to not permanently damage the system."
        ::= { cpqHeSysBatteryEntry 4 }

    cpqHeSysBatteryStatus OBJECT-TYPE
        SYNTAX  INTEGER {
            noError(1),
            generalFailure(2),
            shutdownHighResistance(3),
            shutdownLowVoltage(4),
            shutdownShortCircuit(5),
            shutdownChargeTimeout(6),
            shutdownOverTemperature(7),
            shutdownDischargeMinVoltage(8),
            shutdownDischargeCurrent(9),
            shutdownLoadCountHigh(10),
            shutdownEnablePin(11),
            shutdownOverCurrent(12),
            shutdownPermanentFailure(13),
            shutdownBackupTimeExceeded(14)
            }
        ACCESS  read-only 
        STATUS  mandatory
        DESCRIPTION
            "The status of the battery."
        ::= { cpqHeSysBatteryEntry 5 }

    cpqHeSysBatteryCapacityMaximum OBJECT-TYPE
        SYNTAX  INTEGER
        ACCESS  read-only
        STATUS  mandatory
        DESCRIPTION
            "The maximum capacity of the battery in watts."
        ::= { cpqHeSysBatteryEntry 6 }

    cpqHeSysBatteryProductName OBJECT-TYPE
        SYNTAX  DisplayString (SIZE (0..32))
        ACCESS  read-only
        STATUS  mandatory
        DESCRIPTION
            "The battery product name."
        ::= { cpqHeSysBatteryEntry 7 }

    cpqHeSysBatteryModel OBJECT-TYPE
        SYNTAX  DisplayString (SIZE (0..24))
        ACCESS  read-only
        STATUS  mandatory
        DESCRIPTION
            "The battery model name."
        ::= { cpqHeSysBatteryEntry 8 }

    cpqHeSysBatterySerialNumber OBJECT-TYPE
        SYNTAX  DisplayString (SIZE (0..24))
        ACCESS  read-only
        STATUS  mandatory
        DESCRIPTION
            "The battery serial number."
        ::= { cpqHeSysBatteryEntry 9 }

    cpqHeSysBatteryFirmwareRev OBJECT-TYPE
        SYNTAX  DisplayString (SIZE (0..24))
        ACCESS  read-only
        STATUS  mandatory
        DESCRIPTION
            "The battery firmware revision.  This field will be left
            blank if the firmware revision is unknown."
        ::= { cpqHeSysBatteryEntry 10 }

    cpqHeSysBatterySparePartNum OBJECT-TYPE
        SYNTAX  DisplayString (SIZE (0..24))
        ACCESS  read-only
        STATUS  optional
        DESCRIPTION
            "The battery part number or spare part number."
        ::= { cpqHeSysBatteryEntry 11 }


-- ****************************************************************************
--   HealthMIB Trap Group
--   =====================
--
-- The compaq enterprise               (1.3.6.1.4.1.232)
--      cpqHealth Group                (1.3.6.1.4.1.232.6)
--       cpqHeTrap Group               (1.3.6.1.4.1.232.6.3)  (deprecated)
--
--  The cpqHeTrap group maintains information about the number of traps
--  issued from the health enterprise.  The trap group also maintains a table
--  of the last several traps issued.  This table is intended to give a
--  management application some recent status information immediately upon
--  accessing the agent.
--
--  Implementation of the cpqHeTrap group is optional for agents that
--  support the Server Health MIB.
--
-- ****************************************************************************

    cpqHeTrapPkts OBJECT-TYPE
        SYNTAX  Counter
        ACCESS  read-only
        STATUS  deprecated
        DESCRIPTION
            "The total number of SNMP trap packets issued by the
            Server Health agent."
        ::= { cpqHeTrap 1 }

    cpqHeTrapLogMaxSize OBJECT-TYPE
        SYNTAX  INTEGER (0..2147483647)
        ACCESS  read-only
        STATUS  deprecated
        DESCRIPTION
            "The maximum number of entries that will currently be kept in
            the trap log.  If the maximum size has been reached and a new
            trap occurs the oldest trap will be removed."
        ::= { cpqHeTrap 2 }

-- ****************************************************************************
--   Health MIB Trap Log Table
--   =========================
--
-- The compaq enterprise               (1.3.6.1.4.1.232)
--      cpqHealth Group                (1.3.6.1.4.1.232.6)
--       cpqHeTrap Group               (1.3.6.1.4.1.232.6.3)
--        cpqHeTrapLogTable            (1.3.6.1.4.1.232.6.3.3)  (deprecated)
--
-- ****************************************************************************

    cpqHeTrapLogTable OBJECT-TYPE
        SYNTAX  SEQUENCE OF CpqHeTrapLogEntry
        ACCESS  not-accessible
        STATUS  deprecated
        DESCRIPTION
            "An ordered list of trap log entries (conceptually a queue).  The
            trap log entries will be kept in the order in which they were
            generated with the most recent trap at index 1 and the oldest
            trap entry at index trapLogMaxSize.  If the maximum number of
            entries has been reached and a new trap occurs the oldest trap
            will be removed when the new trap is added so the trapMaxLogSize
            is not exceeded."
        ::= { cpqHeTrap 3 }

    cpqHeTrapLogEntry OBJECT-TYPE
        SYNTAX  CpqHeTrapLogEntry
        ACCESS  not-accessible
        STATUS  deprecated
        DESCRIPTION
            "A description of a trap event."
        INDEX   { cpqHeTrapLogIndex }
        ::= { cpqHeTrapLogTable 1 }

    CpqHeTrapLogEntry ::= SEQUENCE {
        cpqHeTrapLogIndex        INTEGER,
        cpqHeTrapType            INTEGER,
        cpqHeTrapTime            OCTET STRING
    }

    cpqHeTrapLogIndex OBJECT-TYPE
        SYNTAX  INTEGER (0..2147483647)
        ACCESS  read-only
        STATUS  deprecated
        DESCRIPTION
            "The value of this object uniquely identifies this trapLogEntry
             at this time.  The most recent trap will have an index of 1 and
             the oldest trap will have an index of trapLogMaxSize.  Because of
             the queue-like nature of the trapLog this particular trap event's
             index will change as new traps are issued."
        ::= { cpqHeTrapLogEntry 1 }

    cpqHeTrapType OBJECT-TYPE
        SYNTAX  INTEGER {
            cpqHeCorrectableMemoryError(1),
            cpqHeCorrectableMemoryLogDisabled(2),
            cpqHe2CorrectableMemoryError(6001),
            cpqHe2CorrectableMemoryLogDisabled(6002),
            cpqHeThermalTempFailed(6003),
            cpqHeThermalTempDegraded(6004),
            cpqHeThermalTempOk(6005),
            cpqHeThermalSystemFanFailed(6006),
            cpqHeThermalSystemFanDegraded(6007),
            cpqHeThermalSystemFanOk(6008),
            cpqHeThermalCpuFanFailed(6009),
            cpqHeThermalCpuFanOk(6010),
            cpqHeAsrConfirmation(6011),
            cpqHeThermalConfirmation(6012),
            cpqHePostError(6013)
            }
        ACCESS  read-only
        STATUS  deprecated
        DESCRIPTION
            "The type of the trap event this entry describes.  This
             number refers to an entry in a list of traps enumerating the
             possible traps the Server Health agent may issue."
        ::= { cpqHeTrapLogEntry 2 }

    cpqHeTrapTime OBJECT-TYPE
        SYNTAX  OCTET STRING (SIZE (0..6))
        ACCESS  read-only
        STATUS  deprecated
        DESCRIPTION
            "The time of the trap event that this entry describes.  The time
             is given in year (first octet), month, day of month, hour,
             minute, second (last octet) order.  The octets are in Binary
             Coded Decimal (BCD)."
        ::= { cpqHeTrapLogEntry 3 }

-- ****************************************************************************
--  Health MIB Trap Definitions
--  ===========================
--
--  The SNMP trap messages must not be bigger than 484 octets (bytes).
--
--  Trap support in an SNMP agent implementation is optional.  An SNMP
--  agent implementation may support all, some, or none of the traps.
--  If traps are supported, The user should be provided with the option of
--  disabling traps.
-- **************************************************************************

    cpqHeCorrectableMemoryError TRAP-TYPE
        ENTERPRISE cpqHealth
        VARIABLES  { cpqHeCorrMemTotalErrs }
        DESCRIPTION
            "A correctable memory error occurred.

             The error has been corrected.  The current number of correctable
             memory errors is reported in the variable cpqHeCorrMemTotalErrs."

        --#TYPE "Correctable Memory Error Occurred (1)"
        --#SUMMARY "Total correctable errors = %d."
        --#ARGUMENTS {0}
        --#SEVERITY MINOR
        --#TIMEINDEX 99
        --#STATE   OPERATIONAL

        ::= 1

    cpqHeCorrectableMemoryLogDisabled TRAP-TYPE
        ENTERPRISE cpqHealth
        VARIABLES  { cpqHeCorrMemLogStatus }
        DESCRIPTION
            "Correctable memory error tracking disabled.

             The frequency of errors is so high that the error tracking
             logic has been temporarily disabled.  The cpqHeCorrMemLogStatus
             variable indicated the current tracking status."

        --#TYPE "Memory Error Tracking Disabled (2)"
        --#SUMMARY "Too many memory errors - tracking now disabled."
        --#ARGUMENTS {}
        --#SEVERITY CRITICAL
        --#TIMEINDEX 99
        --#STATE   DEGRADED

        ::= 2

-- Trap definitions for Insight Manager version 2.00 and greater
-- use the Compaq Enterprise (232) and have unique trap numbers between all
-- of the MIBs.

    cpqHe2CorrectableMemoryError TRAP-TYPE
        ENTERPRISE compaq
        VARIABLES  { cpqHeCorrMemTotalErrs }
        DESCRIPTION
            "A correctable memory error occurred.

             The error has been corrected.  The current number of correctable
             memory errors is reported in the variable cpqHeCorrMemTotalErrs."

        --#TYPE "Correctable Memory Error Occurred (6001)"
        --#SUMMARY "Total correctable errors = %d."
        --#ARGUMENTS {0}
        --#SEVERITY MINOR
        --#TIMEINDEX 99
        --#STATE   DEGRADED

        ::= 6001

    cpqHe2CorrectableMemoryLogDisabled TRAP-TYPE
        ENTERPRISE compaq
        VARIABLES  { cpqHeCorrMemLogStatus }
        DESCRIPTION
            "Correctable memory error tracking disabled.

             The frequency of errors is so high that the error tracking
             logic has been temporarily disabled.  The cpqHeCorrMemLogStatus
             variable indicated the current tracking status."

        --#TYPE "Memory Error Tracking Disabled (6002)"
        --#SUMMARY "Too many memory errors - tracking now disabled."
        --#ARGUMENTS {}
        --#SEVERITY CRITICAL
        --#TIMEINDEX 99
        --#STATE   DEGRADED

        ::= 6002

    cpqHeThermalTempFailed TRAP-TYPE
        ENTERPRISE compaq
        DESCRIPTION
            "The temperature status has been set to failed.

             The system will be shutdown due to this thermal condition."

        --#TYPE "Thermal Failure (6003)"
        --#SUMMARY "System will be shutdown due to this thermal condition."
        --#ARGUMENTS {}
        --#SEVERITY CRITICAL
        --#TIMEINDEX 99
        --#STATE  DEGRADED

        ::= 6003

    cpqHeThermalTempDegraded TRAP-TYPE
        ENTERPRISE compaq
        VARIABLES  { cpqHeThermalDegradedAction }
        DESCRIPTION
            "The temperature status has been set to degraded.

             The server's temperature is outside of the normal operating
             range.  The server will be shutdown if the
             cpqHeThermalDegradedAction variable is set to shutdown(3)."

        --#TYPE "Thermal Status Degraded (6004)"
        --#SUMMARY "Temperature out of range.  Shutdown may occur."
        --#ARGUMENTS {}
        --#SEVERITY CRITICAL
        --#TIMEINDEX 99
        --#STATE   DEGRADED

        ::= 6004

    cpqHeThermalTempOk TRAP-TYPE
        ENTERPRISE compaq
        DESCRIPTION
            "The temperature status has been set to ok.

             The server's temperature has returned to the normal operating
             range."

        --#TYPE "Temperature OK (6005)"
        --#SUMMARY "Temperature has returned to normal range."
        --#ARGUMENTS {}
        --#SEVERITY INFORMATIONAL
        --#TIMEINDEX 99
        --#STATE OPERATIONAL

        ::= 6005

    cpqHeThermalSystemFanFailed TRAP-TYPE
        ENTERPRISE compaq
        VARIABLES  { cpqHeThermalDegradedAction }
        DESCRIPTION
            "The system fan status has been set to failed.

             A required system fan is not operating normally.  The system
             will be shutdown if the cpqHeThermalDegradedAction variable
             is set to shutdown(3)."

        --#TYPE "System Fan Failure (6006)"
        --#SUMMARY "Required fan not operating normally.  Shutdown may occur."
        --#ARGUMENTS {}
        --#SEVERITY CRITICAL
        --#TIMEINDEX 99
        --#STATE   DEGRADED

        ::= 6006

    cpqHeThermalSystemFanDegraded TRAP-TYPE
        ENTERPRISE compaq
        DESCRIPTION
            "The system fan status has been set to degraded.

             An optional system fan is not operating normally."

        --#TYPE "System Fan Degraded (6007)"
        --#SUMMARY "An optional fan is not operating normally."
        --#ARGUMENTS {}
        --#SEVERITY CRITICAL
        --#TIMEINDEX 99
        --#STATE   DEGRADED

        ::= 6007

    cpqHeThermalSystemFanOk TRAP-TYPE
        ENTERPRISE compaq
        DESCRIPTION
            "The system fan status has been set to ok.

             Any previously non-operational system fans have returned to
             normal operation."

        --#TYPE "System Fan OK (6008)"
        --#SUMMARY "System fan has returned to normal operation."
        --#ARGUMENTS {}
        --#SEVERITY INFORMATIONAL
        --#TIMEINDEX 99
        --#STATE OPERATIONAL

        ::= 6008

    cpqHeThermalCpuFanFailed TRAP-TYPE
        ENTERPRISE compaq
        DESCRIPTION 
            "The CPU fan status has been set to failed.

             A processor fan is not operating normally.  The server will be
             shutdown."

        --#TYPE "CPU Fan Failure (6009)"
        --#SUMMARY "CPU fan has failed.  Server will be shutdown."
        --#ARGUMENTS {}
        --#SEVERITY CRITICAL
        --#TIMEINDEX 99
        --#STATE   NONOPERATIONAL

        ::= 6009

    cpqHeThermalCpuFanOk TRAP-TYPE
        ENTERPRISE compaq
        DESCRIPTION
            "The CPU fan status has been set to ok.

             Any previously non-operational processor fans have returned
             to normal operation."

        --#TYPE "CPU Fan OK (6010)"
        --#SUMMARY "CPU fan is now OK."
        --#ARGUMENTS {}
        --#SEVERITY INFORMATIONAL
        --#TIMEINDEX 99
        --#STATE OPERATIONAL

        ::= 6010

    cpqHeAsrConfirmation TRAP-TYPE
        ENTERPRISE compaq
        DESCRIPTION
            "The server is operational again.

             The server has previously been shutdown by the
             Automatic Server Recovery (ASR) feature and has just
             become operational again."

        --#TYPE "Server Operational (6011)"
        --#SUMMARY "Server is operational again after ASR shutdown."
        --#ARGUMENTS {}
        --#SEVERITY MINOR
        --#TIMEINDEX 99
        --#STATE OPERATIONAL

        ::= 6011

    cpqHeThermalConfirmation TRAP-TYPE
        ENTERPRISE compaq
        DESCRIPTION
            "The server is operational again.

             The server has previously been shutdown due to a thermal
             anomaly on the server and has just become operational again."

        --#TYPE "Server Operational (6012)"
        --#SUMMARY "Server is operational again after thermal shutdown."
        --#ARGUMENTS {}
        --#SEVERITY MINOR
        --#TIMEINDEX 99
        --#STATE OPERATIONAL

        ::= 6012

    cpqHePostError TRAP-TYPE
        ENTERPRISE compaq
        DESCRIPTION
            "One or more POST errors occurred.

             Power On Self-Test (POST) errors occur during the server
             restart process.  "

        --#TYPE "POST Errors Occurred (6013)"
        --#SUMMARY "Errors occurred during server restart."
        --#ARGUMENTS {}
        --#SEVERITY MINOR
        --#TIMEINDEX 99
        --#STATE OPERATIONAL

        ::= 6013

    cpqHeFltTolPwrSupplyDegraded TRAP-TYPE
        ENTERPRISE compaq
        DESCRIPTION
            "The fault tolerant power supply sub-system condition has been
             set to degraded."

        --#TYPE "Server Power Supply Degraded (6014)"
        --#SUMMARY "The server power supply status has become degraded."
        --#ARGUMENTS {}
        --#SEVERITY CRITICAL 
        --#TIMEINDEX 99
        --#STATE   DEGRADED

        ::= 6014


    cpqHe3CorrectableMemoryError TRAP-TYPE
        ENTERPRISE compaq
        VARIABLES  { sysName, cpqHoTrapFlags, cpqHeCorrMemTotalErrs }
        DESCRIPTION
            "A correctable memory error occurred.

             The error has been corrected.  The current number of correctable
             memory errors is reported in the variable cpqHeCorrMemTotalErrs."

        --#TYPE "Correctable Memory Error Occurred (6015)"
        --#SUMMARY "Total correctable errors = %d."
        --#ARGUMENTS {2}
        --#SEVERITY MINOR
        --#TIMEINDEX 99
        --#STATE   DEGRADED


        ::= 6015

    cpqHe3CorrectableMemoryLogDisabled TRAP-TYPE
        ENTERPRISE compaq
        VARIABLES  { sysName, cpqHoTrapFlags, cpqHeCorrMemLogStatus }
        DESCRIPTION
            "Correctable memory error tracking disabled.

             The frequency of errors is so high that the error tracking
             logic has been temporarily disabled.  The cpqHeCorrMemLogStatus
             variable indicated the current tracking status."

        --#TYPE "Memory Error Tracking Disabled (6016)"
        --#SUMMARY "Too many memory errors - tracking now disabled."
        --#ARGUMENTS {}
        --#SEVERITY CRITICAL
        --#TIMEINDEX 99
        --#STATE   DEGRADED
        --#SIMPLE_SEVERITY CRITICAL
        --#HWSTATUS_CATEGORY MEMORY
        
        ::= 6016

    cpqHe3ThermalTempFailed TRAP-TYPE
        ENTERPRISE compaq
        VARIABLES  { sysName, cpqHoTrapFlags }
        DESCRIPTION
            "The temperature status has been set to failed.

             The system will be shutdown due to this thermal condition."

        --#TYPE "Thermal Failure (6017)"
        --#SUMMARY "System will be shutdown due to this thermal condition."
        --#ARGUMENTS {}
        --#SEVERITY CRITICAL
        --#TIMEINDEX 99
        --#STATE  DEGRADED
        --#SIMPLE_SEVERITY CRITICAL
        --#HWSTATUS_CATEGORY THERMAL
        --#ACTION "Check the system for hardware failures and verify the environment is properly cooled."        
                
        ::= 6017

    cpqHe3ThermalTempDegraded TRAP-TYPE
        ENTERPRISE compaq
        VARIABLES  { sysName, cpqHoTrapFlags, cpqHeThermalDegradedAction }
        DESCRIPTION
            "The temperature status has been set to degraded.

             The server's temperature is outside of the normal operating
             range.  The server will be shutdown if the
             cpqHeThermalDegradedAction variable is set to shutdown(3)."

        --#TYPE "Temperature Degraded (6018)"
        --#SUMMARY "Temperature out of range.  Shutdown may occur."
        --#ARGUMENTS {}
        --#SEVERITY CRITICAL
        --#TIMEINDEX 99
        --#STATE   DEGRADED
        --#SIMPLE_SEVERITY CRITICAL
        --#HWSTATUS_CATEGORY THERMAL
        --#ACTION "Check the system for hardware failures and verify the environment is properly cooled." 
        
        ::= 6018

    cpqHe3ThermalTempOk TRAP-TYPE
        ENTERPRISE compaq
        VARIABLES  { sysName, cpqHoTrapFlags }
        DESCRIPTION
            "The temperature status has been set to ok.

             The server's temperature has returned to the normal operating
             range."

        --#TYPE "Temperature OK (6019)"
        --#SUMMARY "Temperature has returned to normal range."
        --#ARGUMENTS {}
        --#SEVERITY INFORMATIONAL
        --#TIMEINDEX 99
        --#STATE OPERATIONAL
        --#SIMPLE_SEVERITY OK
        --#HWSTATUS_CATEGORY THERMAL
        
        ::= 6019

    cpqHe3ThermalSystemFanFailed TRAP-TYPE
        ENTERPRISE compaq
        VARIABLES  { sysName, cpqHoTrapFlags, cpqHeThermalDegradedAction }
        DESCRIPTION
            "The system fan status has been set to failed.

             A required system fan is not operating normally.  The system
             will be shutdown if the cpqHeThermalDegradedAction variable
             is set to shutdown(3)."

        --#TYPE "System Fan Failure (6020)"
        --#SUMMARY "Required fan not operating normally.  Shutdown may occur."
        --#ARGUMENTS {}
        --#SEVERITY CRITICAL
        --#TIMEINDEX 99
        --#STATE   DEGRADED
        --#SIMPLE_SEVERITY CRITICAL
        --#HWSTATUS_CATEGORY FAN
        --#ACTION "Replace the failed fan."       
        
        ::= 6020

    cpqHe3ThermalSystemFanDegraded TRAP-TYPE
        ENTERPRISE compaq
        VARIABLES  { sysName, cpqHoTrapFlags }
        DESCRIPTION
            "The system fan status has been set to degraded.

             An optional system fan is not operating normally."

        --#TYPE "System Fan Degraded (6021)"
        --#SUMMARY "An optional fan is not operating normally."
        --#ARGUMENTS {}
        --#SEVERITY CRITICAL
        --#TIMEINDEX 99
        --#STATE   DEGRADED
        --#SIMPLE_SEVERITY CRITICAL
        --#HWSTATUS_CATEGORY FAN
        --#ACTION "Replace the failing fan."
        
        ::= 6021

    cpqHe3ThermalSystemFanOk TRAP-TYPE
        ENTERPRISE compaq
        VARIABLES  { sysName, cpqHoTrapFlags }
        DESCRIPTION
            "The system fan status has been set to ok.

             Any previously non-operational system fans have returned to
             normal operation."

        --#TYPE "System Fan OK (6022)"
        --#SUMMARY "System fan has returned to normal operation."
        --#ARGUMENTS {}
        --#SEVERITY INFORMATIONAL
        --#TIMEINDEX 99
        --#STATE OPERATIONAL
        --#SIMPLE_SEVERITY OK
        --#HWSTATUS_CATEGORY FAN
        
        ::= 6022

    cpqHe3ThermalCpuFanFailed TRAP-TYPE
        ENTERPRISE compaq
        VARIABLES  { sysName, cpqHoTrapFlags }
        DESCRIPTION
            "The CPU fan status has been set to failed.

             A processor fan is not operating normally.  The server will be
             shutdown."

        --#TYPE "CPU Fan Failure (6023)"
        --#SUMMARY "CPU fan has failed.  Server will be shutdown."
        --#ARGUMENTS {}
        --#SEVERITY CRITICAL
        --#TIMEINDEX 99
        --#STATE   NONOPERATIONAL
        --#SIMPLE_SEVERITY CRITICAL
        --#HWSTATUS_CATEGORY FAN
        --#ACTION "Replace the failed CPU fan."
        
        ::= 6023

    cpqHe3ThermalCpuFanOk TRAP-TYPE
        ENTERPRISE compaq
        VARIABLES  { sysName, cpqHoTrapFlags }
        DESCRIPTION
            "The CPU fan status has been set to ok.

             Any previously non-operational processor fans have returned
             to normal operation."

        --#TYPE "CPU Fan OK (6024)"
        --#SUMMARY "CPU fan is now OK."
        --#ARGUMENTS {}
        --#SEVERITY INFORMATIONAL
        --#TIMEINDEX 99
        --#STATE OPERATIONAL
        --#SIMPLE_SEVERITY OK
        --#HWSTATUS_CATEGORY FAN
        
        ::= 6024

    cpqHe3AsrConfirmation TRAP-TYPE
        ENTERPRISE compaq
        VARIABLES  { sysName, cpqHoTrapFlags }
        DESCRIPTION
            "The server is operational again.

             The server has previously been shutdown by the
             Automatic Server Recovery (ASR) feature and has just
             become operational again."

        --#TYPE "Server Operational (6025)"
        --#SUMMARY "Server is operational again after ASR shutdown."
        --#ARGUMENTS {}
        --#SEVERITY MINOR
        --#TIMEINDEX 99
        --#STATE OPERATIONAL
        --#SIMPLE_SEVERITY MAJOR
        --#HWSTATUS_CATEGORY ASR
	    --#LIFECYCLE
        
        ::= 6025

    cpqHe3ThermalConfirmation TRAP-TYPE
        ENTERPRISE compaq
        VARIABLES  { sysName, cpqHoTrapFlags }
        DESCRIPTION
            "The server is operational again.

             The server has previously been shutdown due to a thermal
             anomaly on the server and has just become operational again."

        --#TYPE "Server Operational (6026)"
        --#SUMMARY "Server is operational again after thermal shutdown."
        --#ARGUMENTS {}
        --#SEVERITY MINOR
        --#TIMEINDEX 99
        --#STATE OPERATIONAL
        --#SIMPLE_SEVERITY MAJOR
        --#HWSTATUS_CATEGORY THERMAL
        
        ::= 6026

    cpqHe3PostError TRAP-TYPE
        ENTERPRISE compaq
        VARIABLES  { sysName, cpqHoTrapFlags }
        DESCRIPTION
            "One or more POST errors occurred.

             Power On Self-Test (POST) errors occur during the server
             restart process. Details of the POST error messages can 
             be found in Integrated Management Log "

        --#TYPE "POST Errors Occurred (6027)"
        --#SUMMARY "Power on self-test errors occurred during server restart."
        --#ARGUMENTS {}
        --#SEVERITY MINOR
        --#TIMEINDEX 99
        --#STATE OPERATIONAL
        --#SIMPLE_SEVERITY MAJOR
        --#HWSTATUS_CATEGORY LOGS
        --#ACTION "Refer to the Integrated Management Log for details on the Power on self-test error."
        
        ::= 6027

    cpqHe3FltTolPwrSupplyDegraded TRAP-TYPE
        ENTERPRISE compaq
        VARIABLES  { sysName, cpqHoTrapFlags }
        DESCRIPTION
            "The fault tolerant power supply sub-system condition has been
             set to degraded."

        --#TYPE "Server Power Supply Degraded (6028)"
        --#SUMMARY "The server power supply status has become degraded."
        --#ARGUMENTS {}
        --#SEVERITY CRITICAL
        --#TIMEINDEX 99
        --#STATE   DEGRADED
        --#SIMPLE_SEVERITY CRITICAL
        --#HWSTATUS_CATEGORY POWER
        --#ACTION "Check the system for a power supply failure. Replace the power supply."
        
        ::= 6028

-- Deprecated in 6.20 trap 6056 is the replacement
    cpqHe3CorrMemReplaceMemModule TRAP-TYPE
        ENTERPRISE compaq
        VARIABLES  { sysName, cpqHoTrapFlags }
        DESCRIPTION
            "A correctable memory log entry indicates a memory module needs
             to be replaced.

             The errors have been corrected, but the memory module should be
             replaced.  The error information is reported in the variable
             cpqHeCorrMemErrDesc."

        --#TYPE "Corr Mem Errors Require a Replacement Memory Module. (6029)"
        --#SUMMARY "Correctable memory errs require a replacement memory module."
        --#ARGUMENTS {}
        --#SEVERITY MINOR
        --#TIMEINDEX 99
        --#STATE   DEGRADED


        ::= 6029


-- Deprecated in 5.10
    cpqHe3FltTolPowerSupplyDegraded TRAP-TYPE
        ENTERPRISE compaq
        VARIABLES  { sysName, cpqHoTrapFlags, cpqHeFltTolPowerSupplyChassis,
                     cpqHeFltTolPowerSupplyBay }
        DESCRIPTION
            "The fault tolerant power supply condition has been set
            to degraded for the specified chassis and bay location."

        --#TYPE "Power Supply Degraded (6030)"
        --#SUMMARY "The Power Supply Degraded on Chassis %d, Bay %d."
        --#ARGUMENTS {2, 3}
        --#SEVERITY CRITICAL
        --#TIMEINDEX 99
        --#STATE   DEGRADED


        ::= 6030

-- Deprecated in 5.10
    cpqHe3FltTolPowerSupplyFailed TRAP-TYPE
        ENTERPRISE compaq
        VARIABLES  { sysName, cpqHoTrapFlags, cpqHeFltTolPowerSupplyChassis,
                     cpqHeFltTolPowerSupplyBay }
        DESCRIPTION
            "The fault tolerant power supply condition has been set
            to failed for the specified chassis and bay location."

        --#TYPE "Power Supply Failed (6031)"
        --#SUMMARY "The Power Supply Failed on Chassis %d, Bay %d."
        --#ARGUMENTS {2, 3}
        --#SEVERITY CRITICAL
        --#TIMEINDEX 99
        --#STATE   NONOPERATIONAL

        ::= 6031

    cpqHe3FltTolPowerRedundancyLost TRAP-TYPE
        ENTERPRISE compaq
        VARIABLES  { sysName, cpqHoTrapFlags, cpqHeFltTolPowerSupplyChassis }
        DESCRIPTION
            "The Fault Tolerant Power Supplies have lost redundancy for
            the specified chassis."

        --#TYPE "Power Redundancy Lost (6032)"
        --#SUMMARY "The power supplies are no longer redundant on chassis %d."
        --#ARGUMENTS {2}
        --#SEVERITY MAJOR
        --#TIMEINDEX 99
        --#STATE   DEGRADED
        --#SIMPLE_SEVERITY MAJOR
        --#HWSTATUS_CATEGORY POWER
        --#ACTION "Check the system power supplies for a failure."
        
        ::= 6032

    cpqHe3FltTolPowerSupplyInserted TRAP-TYPE
        ENTERPRISE compaq
        VARIABLES  { sysName, cpqHoTrapFlags, cpqHeFltTolPowerSupplyChassis,
                     cpqHeFltTolPowerSupplyBay }
        DESCRIPTION
            "A Fault Tolerant Power Supply has been inserted into the
            specified chassis and bay location."

        --#TYPE "Power Supply Inserted (6033)"
        --#SUMMARY "The power supply has been inserted on chassis %d, bay %d."
        --#ARGUMENTS {2, 3}
        --#SEVERITY INFORMATIONAL
        --#TIMEINDEX 99
        --#STATE   OPERATIONAL
        --#SIMPLE_SEVERITY OK
        --#HWSTATUS_CATEGORY POWER
        --#LIFECYCLE
        
        ::= 6033

    cpqHe3FltTolPowerSupplyRemoved TRAP-TYPE
        ENTERPRISE compaq
        VARIABLES  { sysName, cpqHoTrapFlags, cpqHeFltTolPowerSupplyChassis,
                     cpqHeFltTolPowerSupplyBay }
        DESCRIPTION
            "A Fault Tolerant Power Supply has been removed from the
            specified chassis and bay location."

        --#TYPE "Power Supply Removed (6034)"
        --#SUMMARY "The power supply has been removed on chassis %d, bay %d."
        --#ARGUMENTS {2, 3}
        --#SEVERITY MAJOR
        --#TIMEINDEX 99
        --#STATE   DEGRADED
        --#SIMPLE_SEVERITY MAJOR
        --#HWSTATUS_CATEGORY POWER
        --#LIFECYCLE
        
        ::= 6034

    cpqHe3FltTolFanDegraded TRAP-TYPE
        ENTERPRISE compaq
        VARIABLES  { sysName, cpqHoTrapFlags, cpqHeFltTolFanChassis,
                     cpqHeFltTolFanIndex }
        DESCRIPTION
            "The Fault Tolerant Fan condition has been set to degraded
            for the specified chassis and fan."

        --#TYPE "Fan Degraded (6035)"
        --#SUMMARY "The fan degraded on chassis %d, fan %d."
        --#ARGUMENTS {2, 3}
        --#SEVERITY CRITICAL
        --#TIMEINDEX 99
        --#STATE   DEGRADED
        --#SIMPLE_SEVERITY CRITICAL
        --#HWSTATUS_CATEGORY FAN
        --#ACTION "Replace the failing fan."
        
        ::= 6035

    cpqHe3FltTolFanFailed TRAP-TYPE
        ENTERPRISE compaq
        VARIABLES  { sysName, cpqHoTrapFlags, cpqHeFltTolFanChassis,
                     cpqHeFltTolFanIndex }
        DESCRIPTION
            "The Fault Tolerant Fan condition has been set to failed
            for the specified chassis and fan."

        --#TYPE "Fan Failed (6036)"
        --#SUMMARY "The fan failed on chassis %d, fan %d."
        --#ARGUMENTS {2, 3}
        --#SEVERITY CRITICAL
        --#TIMEINDEX 99
        --#STATE   NONOPERATIONAL
        --#SIMPLE_SEVERITY CRITICAL
        --#HWSTATUS_CATEGORY FAN
        --#ACTION "Replace the failed fan."
        
        ::= 6036

    cpqHe3FltTolFanRedundancyLost TRAP-TYPE
        ENTERPRISE compaq
        VARIABLES  { sysName, cpqHoTrapFlags, cpqHeFltTolFanChassis }
        DESCRIPTION
            "The Fault Tolerant Fans have lost redundancy for the
            specified chassis."

        --#TYPE "Fan Redundancy Lost (6037)"
        --#SUMMARY "The fans are no longer redundant on chassis %d." 
        --#ARGUMENTS {2}
        --#SEVERITY MAJOR
        --#TIMEINDEX 99
        --#STATE   DEGRADED
        --#SIMPLE_SEVERITY MAJOR
        --#HWSTATUS_CATEGORY FAN
        --#ACTION "Check the system fans for a failure."
                
        ::= 6037

    cpqHe3FltTolFanInserted TRAP-TYPE
        ENTERPRISE compaq
        VARIABLES  { sysName, cpqHoTrapFlags, cpqHeFltTolFanChassis,
                     cpqHeFltTolFanIndex }
        DESCRIPTION
            "A Fault Tolerant Fan has been inserted into the specified
            chassis and fan location."

        --#TYPE "Fan Inserted (6038)"
        --#SUMMARY "The fan has been inserted on chassis %d, fan %d."
        --#ARGUMENTS {2, 3}
        --#SEVERITY INFORMATIONAL
        --#TIMEINDEX 99
        --#STATE   OPERATIONAL
        --#SIMPLE_SEVERITY OK
        --#HWSTATUS_CATEGORY FAN
        --#LIFECYCLE
        
        ::= 6038

    cpqHe3FltTolFanRemoved TRAP-TYPE
        ENTERPRISE compaq
        VARIABLES  { sysName, cpqHoTrapFlags, cpqHeFltTolFanChassis,
                     cpqHeFltTolFanIndex }
        DESCRIPTION
            "A Fault Tolerant Fan has been removed from the specified
            chassis and fan location."

        --#TYPE "Fan Removed (6039)"
        --#SUMMARY "The fan has been removed on chassis %d, fan %d."
        --#ARGUMENTS {2, 3}
        --#SEVERITY MAJOR
        --#TIMEINDEX 99
        --#STATE   DEGRADED
        --#SIMPLE_SEVERITY MAJOR
        --#HWSTATUS_CATEGORY FAN
        --#LIFECYCLE
        
        ::= 6039

    cpqHe3TemperatureFailed TRAP-TYPE
        ENTERPRISE compaq
        VARIABLES  { sysName, cpqHoTrapFlags, cpqHeTemperatureChassis,
                     cpqHeTemperatureLocale }
        DESCRIPTION
            "The temperature status has been set to failed in the
            specified chassis and location.

            The system will be shutdown due to this condition."

        --#TYPE "Thermal Failure (6040)"
        --#SUMMARY "Temperature exceeded on chassis %d, location %d."
        --#ARGUMENTS {2, 3}
        --#SEVERITY CRITICAL
        --#TIMEINDEX 99
        --#STATE  DEGRADED
        --#SIMPLE_SEVERITY CRITICAL
        --#HWSTATUS_CATEGORY THERMAL
        --#ACTION "Check the system for hardware failures and verify the environment is properly cooled."        
        
        ::= 6040

    cpqHe3TemperatureDegraded TRAP-TYPE
        ENTERPRISE compaq
        VARIABLES  { sysName, cpqHoTrapFlags, cpqHeThermalDegradedAction,
                     cpqHeTemperatureChassis, cpqHeTemperatureLocale }
        DESCRIPTION
            "The temperature status has been set to degraded in the
            specified chassis and location.

            The server's temperature is outside of the normal operating
            range.  The server will be shutdown if the
            cpqHeThermalDegradedAction variable is set to shutdown(3)."

        --#TYPE "Thermal Status Degraded (6041)"
        --#SUMMARY "Temperature out of range on chassis %d, location %d. Shutdown may occur."
        --#ARGUMENTS {3, 4}
        --#SEVERITY CRITICAL
        --#TIMEINDEX 99
        --#STATE   DEGRADED
        --#SIMPLE_SEVERITY CRITICAL
        --#HWSTATUS_CATEGORY THERMAL
        --#ACTION "Check the system for hardware failures and verify the environment is properly cooled."
        
        ::= 6041

    cpqHe3TemperatureOk TRAP-TYPE
        ENTERPRISE compaq
        VARIABLES  { sysName, cpqHoTrapFlags, cpqHeTemperatureChassis,
                     cpqHeTemperatureLocale }
        DESCRIPTION
            "The temperature status has been set to ok in the
            specified chassis and location.

            The server's temperature has returned to the normal operating
            range."

        --#TYPE "Thermal Status OK (6042)"
        --#SUMMARY "Temperature normal on chassis %d, location %d."
        --#ARGUMENTS {2, 3}
        --#SEVERITY INFORMATIONAL
        --#TIMEINDEX 99
        --#STATE OPERATIONAL
        --#SIMPLE_SEVERITY OK
        --#HWSTATUS_CATEGORY THERMAL
        
        ::= 6042

    cpqHe3PowerConverterDegraded TRAP-TYPE
        ENTERPRISE compaq
        VARIABLES  { sysName, cpqHoTrapFlags, cpqHePwrConvChassis,
                     cpqHePwrConvSlot, cpqHePwrConvSocket }
        DESCRIPTION
            "The DC-DC Power Converter condition has been set to degraded
            for the specified chassis, slot and socket."

        --#TYPE "Power Converter Degraded (6043)"
        --#SUMMARY "The power converter degraded on chassis %d, slot %d, socket %d."
        --#ARGUMENTS {2, 3, 4}
        --#SEVERITY CRITICAL
        --#TIMEINDEX 99
        --#STATE   DEGRADED
        --#SIMPLE_SEVERITY CRITICAL
        --#HWSTATUS_CATEGORY POWER
        --#ACTION "Check for a failing power converter or for a failed power converter in a redundant pair. Replace the power converter."
        

        ::= 6043

    cpqHe3PowerConverterFailed TRAP-TYPE
        ENTERPRISE compaq
        VARIABLES  { sysName, cpqHoTrapFlags, cpqHePwrConvChassis,
                     cpqHePwrConvSlot, cpqHePwrConvSocket }
        DESCRIPTION
            "The DC-DC Power Converter condition has been set to failed
            for the specified chassis, slot and socket."

        --#TYPE "Power Converter Failed (6044)"
        --#SUMMARY "The power converter failed on chassis %d, slot %d, socket %d."
        --#ARGUMENTS {2, 3, 4}
        --#SEVERITY CRITICAL
        --#TIMEINDEX 99
        --#STATE   NONOPERATIONAL
        --#SIMPLE_SEVERITY CRITICAL
        --#HWSTATUS_CATEGORY POWER
        --#ACTION "Replace the failed power converter."
        
        ::= 6044

    cpqHe3PowerConverterRedundancyLost TRAP-TYPE
        ENTERPRISE compaq
        VARIABLES  { sysName, cpqHoTrapFlags, cpqHePwrConvChassis }
        DESCRIPTION
            "The DC-DC Power Converters have lost redundancy for the
            specified chassis."

        --#TYPE "Power Converter Redundancy Lost (6045)"
        --#SUMMARY "The power converters are no longer redundant on chassis %d."
        --#ARGUMENTS {2}
        --#SEVERITY CRITICAL
        --#TIMEINDEX 99
        --#STATE   DEGRADED
        --#SIMPLE_SEVERITY CRITICAL
        --#HWSTATUS_CATEGORY POWER
        --#ACTION "Check the power converters in the system for a failure in a redundant pair. Replace the power converter."  


        ::= 6045

    cpqHe3CacheAccelParityError TRAP-TYPE
        ENTERPRISE compaq
        VARIABLES  { sysName, cpqHoTrapFlags }
        DESCRIPTION
            "A cache accelerator parity error indicates a cache module
             needs to be replaced.

             The error information is reported in the variable
             cpqHeEventLogErrorDesc."

        --#TYPE "Cache Accel Parity Errors may require a module. (6046)"
        --#SUMMARY "Cache accelerator errors may require a replacement module."
        --#ARGUMENTS {}
        --#SEVERITY CRITICAL
        --#TIMEINDEX 99
        --#STATE   NONOPERATIONAL
        --#SIMPLE_SEVERITY CRITICAL
        --#HWSTATUS_CATEGORY MEMORY      
        --#ACTION "Refer to the Integrated Management Log for details on the error. Replace the cache module."


        ::= 6046

    cpqHeResilientMemOnlineSpareEngaged TRAP-TYPE
        ENTERPRISE compaq
        VARIABLES  { sysName, cpqHoTrapFlags }
        DESCRIPTION
           "Advanced Memory Protection Online Spare Engaged.

           The Advanced Memory Protection subsystem has detected a memory
           fault. The Online Spare Memory has been activated.

           User Action: Schedule server down-time to replace the faulty
           memory."

        --#TYPE "Online Spare Memory Engaged (6047)"
        --#SUMMARY "The Advanced Memory Protection subsystem has engaged the online spare memory."
        --#ARGUMENTS {}
        --#SEVERITY MAJOR
        --#TIMEINDEX 99
        --#STATE DEGRADED
        --#SIMPLE_SEVERITY MAJOR
        --#HWSTATUS_CATEGORY MEMORY
        --#ACTION "Schedule server down-time to replace the faulty memory."
        
        ::= 6047

-- New for rev 5.10.
    cpqHe4FltTolPowerSupplyOk TRAP-TYPE
        ENTERPRISE compaq
        VARIABLES  { sysName, cpqHoTrapFlags, cpqHeFltTolPowerSupplyChassis,
                     cpqHeFltTolPowerSupplyBay, cpqHeFltTolPowerSupplyStatus,
                     cpqHeFltTolPowerSupplyModel, cpqHeFltTolPowerSupplySerialNumber,
                     cpqHeFltTolPowerSupplyAutoRev, cpqHeFltTolPowerSupplyFirmwareRev,
                     cpqHeFltTolPowerSupplySparePartNum, cpqSiServerSystemId }
        DESCRIPTION
            "The fault tolerant power supply condition has been set back
            to the OK state for the specified chassis and bay location."

        --#TYPE "Power Supply OK (6048)"
        --#SUMMARY "The power supply is ok on chassis %d, bay %d, status %d, model %s, serial number %s, firmware %s."
        --#ARGUMENTS {2, 3, 4, 5, 6, 8}
        --#SEVERITY INFORMATIONAL
        --#TIMEINDEX 99
        --#STATE OPERATIONAL
        --#SIMPLE_SEVERITY OK
        --#HWSTATUS_CATEGORY POWER
        
        ::= 6048

-- New for rev 5.10.  Deprecated cpqHe3FltTolPowerSupplyDegraded
    cpqHe4FltTolPowerSupplyDegraded TRAP-TYPE
        ENTERPRISE compaq
        VARIABLES  { sysName, cpqHoTrapFlags, cpqHeFltTolPowerSupplyChassis,
                     cpqHeFltTolPowerSupplyBay, cpqHeFltTolPowerSupplyStatus,
                     cpqHeFltTolPowerSupplyModel, cpqHeFltTolPowerSupplySerialNumber,
                     cpqHeFltTolPowerSupplyAutoRev, cpqHeFltTolPowerSupplyFirmwareRev,
                     cpqHeFltTolPowerSupplySparePartNum, cpqSiServerSystemId }
        DESCRIPTION
            "The fault tolerant power supply condition has been set
            to degraded for the specified chassis and bay location."

        --#TYPE "Power Supply Degraded (6049)"
        --#SUMMARY "The power supply is degraded on chassis %d, bay %d, status %d, model %s, serial number %s, firmware %s."
        --#ARGUMENTS {2, 3, 4, 5, 6, 8}
        --#SEVERITY CRITICAL
        --#TIMEINDEX 99
        --#STATE DEGRADED
        --#SIMPLE_SEVERITY CRITICAL
        --#HWSTATUS_CATEGORY POWER
        --#ACTION "Replace the failing power supply."
        
        ::= 6049

-- New for rev 5.10.  Deprecated cpqHe3FltTolPowerSupplyFailed
    cpqHe4FltTolPowerSupplyFailed TRAP-TYPE
        ENTERPRISE compaq
        VARIABLES  { sysName, cpqHoTrapFlags, cpqHeFltTolPowerSupplyChassis,
                     cpqHeFltTolPowerSupplyBay, cpqHeFltTolPowerSupplyStatus,
                     cpqHeFltTolPowerSupplyModel, cpqHeFltTolPowerSupplySerialNumber,
                     cpqHeFltTolPowerSupplyAutoRev, cpqHeFltTolPowerSupplyFirmwareRev,
                     cpqHeFltTolPowerSupplySparePartNum, cpqSiServerSystemId }
        DESCRIPTION
            "The fault tolerant power supply condition has been set
            to failed for the specified chassis and bay location."

        --#TYPE "Power Supply Failed (6050)"
        --#SUMMARY "The power supply is failed on chassis %d, bay %d, status %d, model %s, serial number %s, firmware %s."
        --#ARGUMENTS {2, 3, 4, 5, 6, 8}
        --#SEVERITY CRITICAL
        --#TIMEINDEX 99
        --#STATE NONOPERATIONAL
        --#SIMPLE_SEVERITY CRITICAL
        --#HWSTATUS_CATEGORY POWER
        --#ACTION "Replace the failed power supply."
                
        ::= 6050

-- New for rev 5.40.
    cpqHeResilientMemMirroredMemoryEngaged TRAP-TYPE
        ENTERPRISE compaq
        VARIABLES  { sysName, cpqHoTrapFlags }
        DESCRIPTION
           "Advanced Memory Protection Mirrored Memory Engaged.

           The Advanced Memory Protection subsystem has detected a memory
           fault. Mirrored Memory has been activated.

           User Action: Replace the faulty memory."

        --#TYPE "Mirrored Memory Engaged (6051)"
        --#SUMMARY "The Advanced Memory Protection subsystem has engaged the online spare memory."
        --#ARGUMENTS {}
        --#SEVERITY MAJOR
        --#TIMEINDEX 99
        --#STATE DEGRADED
        --#SIMPLE_SEVERITY MAJOR
        --#HWSTATUS_CATEGORY MEMORY
        --#ACTION "Replace the faulty memory."
                
        ::= 6051

-- New for rev 5.50.
    cpqHeResilientAdvancedECCMemoryEngaged TRAP-TYPE
        ENTERPRISE compaq
        VARIABLES  { sysName, cpqHoTrapFlags }
        DESCRIPTION
           "Advanced Memory Protection Advanced ECC Memory Engaged.

           The Advanced Memory Protection subsystem has detected a memory
           fault. Advanced ECC has been activated.

           User Action: Replace the faulty memory."

        --#TYPE "Advanced ECC Memory Engaged (6052)"
        --#SUMMARY "The Advanced Memory Protection subsystem has engaged the advanced ECC memory."
        --#ARGUMENTS {}
        --#SEVERITY MAJOR
        --#TIMEINDEX 99
        --#STATE DEGRADED
        --#SIMPLE_SEVERITY MAJOR
        --#HWSTATUS_CATEGORY MEMORY
        --#ACTION "Replace the faulty memory."
                
        ::= 6052

-- New traps added for 6.20.

    cpqHeResilientMemXorMemoryEngaged TRAP-TYPE
        ENTERPRISE compaq
        VARIABLES  { sysName, cpqHoTrapFlags }
        DESCRIPTION
           "Advanced Memory Protection XOR Engine Memory Engaged.

           The Advanced Memory Protection subsystem has detected a memory
           fault. The XOR engine has been activated.

           User Action: Replace the faulty memory."

        --#TYPE "Advanced XOR Memory Engaged (6053)"
        --#SUMMARY "The Advanced Memory Protection subsystem has engaged the XOR memory."
        --#ARGUMENTS {}
        --#SEVERITY MAJOR
        --#TIMEINDEX 99
        --#STATE DEGRADED
        --#SIMPLE_SEVERITY MAJOR
        --#HWSTATUS_CATEGORY MEMORY
        --#ACTION "Replace the faulty memory."
        
        ::= 6053

    cpqHe3FltTolPowerRedundancyRestored TRAP-TYPE
        ENTERPRISE compaq
        VARIABLES  { sysName, cpqHoTrapFlags, cpqHeFltTolPowerSupplyChassis }
        DESCRIPTION
            "The Fault Tolerant Power Supplies have returned to a redundant
            state for the specified chassis."

        --#TYPE "Power Redundancy Restored (6054)"
        --#SUMMARY "The power supplies are now redundant on chassis %d."
        --#ARGUMENTS {2}
        --#SEVERITY INFORMATIONAL
        --#TIMEINDEX 99
        --#STATE OPERATIONAL
        --#SIMPLE_SEVERITY OK
        --#HWSTATUS_CATEGORY POWER
        
        ::= 6054

    cpqHe3FltTolFanRedundancyRestored TRAP-TYPE
        ENTERPRISE compaq
        VARIABLES  { sysName, cpqHoTrapFlags, cpqHeFltTolFanChassis }
        DESCRIPTION
            "The Fault Tolerant Fans have returned to a redundant state for
            the specified chassis."

        --#TYPE "Fan Redundancy Restored (6055)"
        --#SUMMARY "The fans are now redundant on chassis %d."
        --#ARGUMENTS {2}
        --#SEVERITY INFORMATIONAL
        --#TIMEINDEX 99
        --#STATE OPERATIONAL
        --#SIMPLE_SEVERITY OK
        --#HWSTATUS_CATEGORY FAN
        
        ::= 6055

-- Updated for 6.20 trap replaced 6029
-- deprecateed in 8.20 replaced with 6064
    cpqHe4CorrMemReplaceMemModule TRAP-TYPE
        ENTERPRISE compaq
        VARIABLES  { sysName, cpqHoTrapFlags, cpqHeResMemBoardIndex,
                     cpqHeResMemModuleIndex, cpqHeResMemModuleSparePartNo,
                     cpqSiMemModuleSize, cpqSiServerSystemId }
        DESCRIPTION
            "Corrected Memory Errors Detected

             The errors have been corrected, but the memory module should be
             replaced."

        --#TYPE "Corrected Memory Errors - Replace Memory Module. (6056)"
        --#SUMMARY "Correctable memory errors require a replacement of the memory module in slot %d, socket %d."
        --#ARGUMENTS {2, 3}
        --#SEVERITY MINOR
        --#TIMEINDEX 99
        --#STATE   DEGRADED

        ::= 6056

-- deprecateed in 8.20 replaced with 6065
    cpqHeResMemBoardRemoved TRAP-TYPE
        ENTERPRISE compaq
        VARIABLES  { sysName, cpqHoTrapFlags, cpqHeResMemBoardSlotIndex }
        DESCRIPTION 
           "Memory board or cartridge removed.

           An Advanced Memory Protection sub-system board or cartridge has
           been removed from the system.

           User Action: Insure the board or cartridge has memory correctly
           installed and re-insert the memory board or cartridge back into
           the system."

        --#TYPE "Memory Board or Cartridge Removed (6057)"
        --#SUMMARY "Memory Board or Cartridge Removed from Slot %d."
        --#ARGUMENTS {2}
        --#SEVERITY MAJOR
        --#TIMEINDEX 99
        --#STATE OPERATIONAL
        ::= 6057

-- deprecateed in 8.20 replaced with 6066
    cpqHeResMemBoardInserted TRAP-TYPE
        ENTERPRISE compaq
        VARIABLES  { sysName, cpqHoTrapFlags, cpqHeResMemBoardSlotIndex }
        DESCRIPTION
           "Memory board or cartridge inserted.

           An Advanced Memory Protection sub-system board or cartridge has
           been inserted into the system.

           User Action: None."

        --#TYPE "Memory Board or Cartridge Inserted (6058)"
        --#SUMMARY "Memory Board or Cartridge Inserted into Slot %d."
        --#ARGUMENTS {2}
        --#SEVERITY INFORMATIONAL
        --#TIMEINDEX 99
        --#STATE OPERATIONAL
        ::= 6058

-- deprecateed in 8.20 replaced with 6067
    cpqHeResMemBoardBusError TRAP-TYPE
        ENTERPRISE compaq
        VARIABLES  { sysName, cpqHoTrapFlags, cpqHeResMemBoardSlotIndex }
        DESCRIPTION
           "Memory board or cartridge bus error detected.

           An Advanced Memory Protection sub-system board or cartridge
           bus error has been detected.

           User Action: Replace the indicated board or cartridge."

        --#TYPE "Memory Board or Cartridge Bus Error Detected (6059)"
        --#SUMMARY "Memory Board or Cartridge Bus Error Detected in Slot %d."
        --#ARGUMENTS {2}
        --#SEVERITY CRITICAL
        --#TIMEINDEX 99
        --#STATE DEGRADED
        ::= 6059

-- The follow trap 6060 is supported only in Tru64 at this time.
-- This trap is not currently supported for ProLiants.
    cpqHeEventOccurred TRAP-TYPE
        ENTERPRISE compaq
        VARIABLES  { sysName, cpqHoTrapFlags, cpqHeEventLogEntryNumber,
                     cpqHeEventLogEntrySeverity, cpqHeEventLogUpdateTime,
                     cpqHeEventLogErrorDesc }
        DESCRIPTION
           "An event has occurred.
           User Action: None."

        --#TYPE "Event has occurred (6060)"
        --#SUMMARY "Event %s has occurred, severity %d "
        --#ARGUMENTS {5,3}
        --#SEVERITY INFORMATIONAL
        --#TIMEINDEX 99
        --#STATE OPERATIONAL
        --#SIMPLE_SEVERITY OK
        --#HWSTATUS_CATEGORY NONE        
        ::= 6060

cpqHeManagementProcInReset TRAP-TYPE
        ENTERPRISE compaq
        VARIABLES  { sysName, cpqHoTrapFlags }
        DESCRIPTION
            "The Management processor is currently in reset

             The management processor is currently in the process of being reset
             because of a firmware update or some other event.

             User action: None"

        --#TYPE "Management processor is currently in reset. (6061)"
        --#SUMMARY "The management processor is in the process of being reset."
        --#ARGUMENTS {}
        --#SEVERITY MINOR
        --#TIMEINDEX 99
        --#STATE   DEGRADED
        --#SIMPLE_SEVERITY MAJOR
        --#HWSTATUS_CATEGORY MANAGEMENTPROCESSOR
        
        ::= 6061

    cpqHeManagementProcReady TRAP-TYPE
        ENTERPRISE compaq
        VARIABLES  { sysName, cpqHoTrapFlags }
        DESCRIPTION
            "The Management processor is ready

             The management processor has successfully reset and is now available
             again.

             User action: None"

        --#TYPE "Management processor is ready. (6062)"
        --#SUMMARY "The management processor is ready after a successful reset."
        --#ARGUMENTS {}
        --#SEVERITY INFORMATIONAL
        --#TIMEINDEX 99
        --#STATE OPERATIONAL
        --#SIMPLE_SEVERITY OK
        --#HWSTATUS_CATEGORY MANAGEMENTPROCESSOR
        
        ::= 6062

    cpqHeManagementProcFailedReset TRAP-TYPE
        ENTERPRISE compaq
        VARIABLES  { sysName, cpqHoTrapFlags }
        DESCRIPTION
            "The Management processor failed reset

             The management processor was not successfully reset and is not 
             operational.

             User action: Reset the management procesessor again or re-flash
             the management processor firmware."

        --#TYPE "Management processor failed reset. (6063)"
        --#SUMMARY "The management processor failed reset."
        --#ARGUMENTS {}
        --#SEVERITY CRITICAL
        --#TIMEINDEX 99
        --#STATE   NONOPERATIONAL
        --#SIMPLE_SEVERITY CRITICAL
        --#HWSTATUS_CATEGORY MANAGEMENTPROCESSOR
        --#ACTION "Reset the management procesessor again or re-flash the management processor firmware."
                
        ::= 6063

-- Updated for 8.20 trap replaced 6056
    cpqHe5CorrMemReplaceMemModule TRAP-TYPE
        ENTERPRISE compaq
        VARIABLES  { sysName, cpqHoTrapFlags, cpqHeResMem2BoardNum, 
                     cpqHeResMem2CpuNum, cpqHeResMem2RiserNum, 
                     cpqHeResMem2ModuleNum, cpqHeResMem2ModulePartNo, 
                     cpqHeResMem2ModuleSize, cpqSiServerSystemId }
        DESCRIPTION
            "Corrected \ uncorrected Memory Errors Detected

             The errors have been corrected, but the memory module should be
             replaced. Value 0 for CPU means memory is not Processor based"

        --#TYPE "Corrected \ uncorrectable Memory Errors - Replace Memory Module. (6064)"
        --#SUMMARY "Correctable \ uncorrectable memory errors require a replacement of the memory module in slot %d, cpu %d, riser %d, socket %d."
        --#ARGUMENTS {2, 3, 4, 5}
        --#SEVERITY MAJOR
        --#TIMEINDEX 99
        --#STATE   DEGRADED
        --#SIMPLE_SEVERITY MAJOR
        --#HWSTATUS_CATEGORY MEMORY
        --#ACTION "Replace the failing memory module."
        
        ::= 6064

-- Updated for 8.20 trap replaced 6057
    cpqHe5ResMemBoardRemoved TRAP-TYPE
        ENTERPRISE compaq
        VARIABLES  { sysName, cpqHoTrapFlags, cpqHeResMem2BoardSlotNum, cpqHeResMem2BoardCpuNum, cpqHeResMem2BoardRiserNum }
        DESCRIPTION 
           "Memory board or cartridge or riser removed.

           An Advanced Memory Protection sub-system board or cartridge or riser has
           been removed from the system. Value 0 for CPU means memory is not processor based.

           User Action: Insure the board or cartridge or riser has memory correctly
           installed and re-insert the memory board or cartridge or CPU back into
           the system."

        --#TYPE "Memory Board or Cartridge or Riser Removed (6065)"
        --#SUMMARY "Memory board or cartridge or riser removed from slot %d, CPU %d, riser %d."
        --#ARGUMENTS {2,3,4}
        --#SEVERITY MAJOR
        --#TIMEINDEX 99
        --#STATE OPERATIONAL
        --#SIMPLE_SEVERITY MAJOR
        --#HWSTATUS_CATEGORY MEMORY
        --#LIFECYCLE   
        ::= 6065

-- Updated for 8.20 trap replaced 6058
    cpqHe5ResMemBoardInserted TRAP-TYPE
        ENTERPRISE compaq
        VARIABLES  { sysName, cpqHoTrapFlags, cpqHeResMem2BoardSlotNum, cpqHeResMem2BoardCpuNum, cpqHeResMem2BoardRiserNum }
        DESCRIPTION
           "Memory board or cartridge or riser inserted.

           An Advanced Memory Protection sub-system board or cartridge or riser 
           Has been inserted into the system. Value 0 for CPU means memory is not processor based.

           User Action: None."

        --#TYPE "Memory Board or Cartridge Inserted (6066)"
        --#SUMMARY "Memory board or cartridge inserted into slot %d, CPU %d, riser %d."
        --#ARGUMENTS {2,3,4}
        --#SEVERITY INFORMATIONAL
        --#TIMEINDEX 99
        --#STATE OPERATIONAL
        --#SIMPLE_SEVERITY OK
        --#HWSTATUS_CATEGORY MEMORY
        --#LIFECYCLE  
        ::= 6066

-- Updated for 8.20 trap replaced 6059
    cpqHe5ResMemBoardBusError TRAP-TYPE
        ENTERPRISE compaq
        VARIABLES  { sysName, cpqHoTrapFlags, cpqHeResMem2BoardSlotNum, cpqHeResMem2BoardCpuNum, cpqHeResMem2BoardRiserNum }
        DESCRIPTION
           "Memory board or cartridge or Riser bus error detected.

           An Advanced Memory Protection sub-system board or cartridge or Riser
           bus error has been detected. Value 0 for CPU means memory is not processor based.

           User Action: Replace the indicated board or cartridge or Riser."

        --#TYPE "Memory Board or Cartridge or Riser Bus Error Detected (6067)"
        --#SUMMARY "Memory board or cartridge bus error detected in slot %d, CPU %d, riser %d."
        --#ARGUMENTS {2,3,4}
        --#SEVERITY CRITICAL
        --#TIMEINDEX 99
        --#STATE DEGRADED
        --#SIMPLE_SEVERITY CRITICAL
        --#HWSTATUS_CATEGORY MEMORY     
        --#ACTION "Replace the indicated board, cartridge, or riser."           
        ::= 6067

-- Added for 8.20
    cpqHeResilientMemLockStepMemoryEngaged TRAP-TYPE
        ENTERPRISE compaq
        VARIABLES  { sysName, cpqHoTrapFlags }
        DESCRIPTION
           "Advanced Memory Protection LockStep Engine Memory Engaged.

           The Advanced Memory Protection subsystem has detected a memory
           fault. The LockStep engine has been activated.

           User Action: Replace the faulty memory."

        --#TYPE "Advanced LockStep Memory Engaged (6068)"
        --#SUMMARY "The Advanced Memory Protection subsystem has engaged the LockStep memory."
        --#ARGUMENTS {}
        --#SEVERITY MAJOR
        --#TIMEINDEX 99
        --#STATE DEGRADED
        --#SIMPLE_SEVERITY MAJOR
        --#HWSTATUS_CATEGORY MEMORY
        --#ACTION "Replace the faulty memory."
        
        ::= 6068

-- New for rev 8.30.
    cpqHe4FltTolPowerSupplyACpowerloss TRAP-TYPE
        ENTERPRISE compaq
        VARIABLES  { sysName, cpqHoTrapFlags, cpqHeFltTolPowerSupplyChassis,
                     cpqHeFltTolPowerSupplyBay, cpqHeFltTolPowerSupplyStatus,
                     cpqHeFltTolPowerSupplyModel, cpqHeFltTolPowerSupplySerialNumber,
                     cpqHeFltTolPowerSupplyAutoRev, cpqHeFltTolPowerSupplyFirmwareRev,
                     cpqHeFltTolPowerSupplySparePartNum, cpqSiServerSystemId }
        DESCRIPTION
            "The fault tolerant power supply AC power loss for the specified chassis and bay location."

        --#TYPE "Power Supply AC Power Loss (6069)"
        --#SUMMARY "The power supply AC power loss in %d, bay %d, status %d, model %s, serial number %s, firmware %s."
        --#ARGUMENTS {2, 3, 4, 5, 6, 8}
        --#SEVERITY CRITICAL
        --#TIMEINDEX 99
        --#STATE NONOPERATIONAL
        --#SIMPLE_SEVERITY CRITICAL
        --#HWSTATUS_CATEGORY POWER
        --#ACTION "Check the power source for the specified power supply."
        
        ::= 6069

-- New for rev 10.0.
	cpqHeSysBatteryFailed TRAP-TYPE
        ENTERPRISE compaq
        VARIABLES  { sysName, cpqHoTrapFlags, cpqHoGUIDCanonical,
                     cpqHeSysBatteryChassis, cpqHeSysBatteryIndex,
                     cpqHeSysBatteryStatus, cpqHeSysBatteryModel,
                     cpqHeSysBatterySerialNumber, cpqHeSysBatterySparePartNum }
        DESCRIPTION
            "The system battery condition has been set to failed
            for the specified chassis and index location."

        --#TYPE "System Battery Failed (6070)"
        --#SUMMARY "The Battery Has Failed on Chassis %d, Index %d, Status %d, Model %s, Serial Num %s, Spare Part %s."
        --#ARGUMENTS {3, 4, 5, 6, 7, 8}
        --#SEVERITY MAJOR
        --#TIMEINDEX 99
        --#STATE DEGRADED 
        --#SIMPLE_SEVERITY MAJOR
        --#HWSTATUS_CATEGORY BATTERY
        --#ACTION "Replace the failed battery."
        
        ::= 6070

    cpqHeSysBatteryRemoved TRAP-TYPE
        ENTERPRISE compaq
        VARIABLES  { sysName, cpqHoTrapFlags, cpqHoGUIDCanonical,
                     cpqHeSysBatteryChassis, cpqHeSysBatteryIndex }
        DESCRIPTION
            "The system battery condition has removed
            for the specified chassis and index location."

        --#TYPE "System Battery Removed (6071)"
        --#SUMMARY "The Battery Has Been Removed on Chassis %d, Index %d."
        --#ARGUMENTS {3, 4 }
        --#SEVERITY MAJOR
        --#TIMEINDEX 99
        --#STATE DEGRADED 
        --#SIMPLE_SEVERITY MAJOR
        --#HWSTATUS_CATEGORY BATTERY
        --#LIFECYCLE
        
        ::= 6071
END
